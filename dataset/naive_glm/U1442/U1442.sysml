package LiquidCoolingSystem {
    import ScalarValues::*;
    import ISQ::*;
    import ISQSpace::*;
    import ISQThermodynamics::*;
    import ISQMechanics::*;

    // ---------- Value Types ----------
    def TemperatureValue = RealValue { unit "°C"; }
    def FlowRateValue = RealValue { unit "L/min"; }
    def PressureValue = RealValue { unit "bar"; }
    def PowerValue = RealValue { unit "W"; }
    def SpeedValue = RealValue { unit "rpm"; }
    def ValvePositionValue = RealValue { unit "%"; }
    def HeatFluxValue = RealValue { unit "W"; }

    attribute targetTemp : TemperatureValue = 45.0;
    attribute maxSafeTemp : TemperatureValue = 85.0;
    attribute maxCoolingThreshold : TemperatureValue = 70.0;
    attribute standbyFlowRate : FlowRateValue = 0.5;
    attribute normalFlowRate : FlowRateValue = 2.0;
    attribute maxFlowRate : FlowRateValue = 4.0;

    // ---------- Item Types ----------
    item def Coolant {
        attribute specificHeat : RealValue { unit "J/(kg*K)"; } = 4200.0;
        attribute density : RealValue { unit "kg/m^3"; } = 1050.0;
        attribute currentTemp : TemperatureValue;
        attribute flowRate : FlowRateValue;
    }

    item def AmbientAir {
        attribute temperature : TemperatureValue = 25.0;
    }

    // ---------- Port Definitions ----------
    port def CoolantPort {
        out item coolantFlow : Coolant;
    }

    port def CoolantInPort {
        in item coolantFlow : Coolant;
    }

    port def TempSensorPort {
        out attribute measuredTemp : TemperatureValue;
    }

    port def PumpControlPort {
        in attribute commandedSpeed : SpeedValue;
    }

    port def ValveControlPort {
        in attribute commandedPosition : ValvePositionValue;
    }

    port def HeatInputPort {
        in attribute heatFlux : HeatFluxValue;
    }

    // ---------- Pump ----------
    part def Pump {
        port coolantIn : CoolantInPort;
        port coolantOut : CoolantPort;
        port control : PumpControlPort;

        attribute currentSpeed : SpeedValue;
        attribute powerConsumption : PowerValue;
        attribute maxSpeed : SpeedValue = 5000.0;

        state def PumpStates {
            entry; then Standby;

            state Standby {
                entry action { currentSpeed = 0.0; powerConsumption = 5.0; }
                transition Standby_Normal first Standby
                    when (control.commandedSpeed > 0.0 and control.commandedSpeed < 4000.0)
                    then Normal;
                transition Standby_HighSpeed first Standby
                    when (control.commandedSpeed >= 4000.0)
                    then HighSpeed;
            }

            state Normal {
                entry action { currentSpeed = 3000.0; powerConsumption = 50.0; }
                transition Normal_Standby first Normal
                    when (control.commandedSpeed == 0.0)
                    then Standby;
                transition Normal_HighSpeed first Normal
                    when (control.commandedSpeed >= 4000.0)
                    then HighSpeed;
            }

            state HighSpeed {
                entry action { currentSpeed = maxSpeed; powerConsumption = 120.0; }
                transition HighSpeed_Normal first HighSpeed
                    when (control.commandedSpeed > 0.0 and control.commandedSpeed < 4000.0)
                    then Normal;
                transition HighSpeed_Standby first HighSpeed
                    when (control.commandedSpeed == 0.0)
                    then Standby;
            }
        }

        part pumpStateMachine : PumpStates;

        action def CirculateCoolant {
            in coolantIn : CoolantInPort;
            out coolantOut : CoolantPort;
            in speed : SpeedValue;
            
            assert constraint { speed >= 0.0 and speed <= maxSpeed }
        }

        perform CirculateCoolant;
    }

    // ---------- Heat Source ----------
    part def HeatSource {
        port coolantIn : CoolantInPort;
        port coolantOut : CoolantPort;
        port heatInput : HeatInputPort;
        port sensorPort : TempSensorPort;

        attribute surfaceTemp : TemperatureValue;
        attribute thermalResistance : RealValue { unit "K/W"; } = 0.15;
        attribute heatDissipation : HeatFluxValue;

        action def AbsorbHeat {
            in coolantIn : CoolantInPort;
            out coolantOut : CoolantPort;
            in heatFlux : HeatFluxValue;
            
            attribute deltaT : TemperatureValue;
            
            // Heat absorbed by coolant = heat generated by component
            constraint { coolantOut.coolantFlow.currentTemp == coolantIn.coolantFlow.currentTemp + deltaT }
            constraint { deltaT == heatFlux / (coolantIn.coolantFlow.flowRate * 60.0 * 4200.0 * 1050.0 / 1000.0) }
        }

        perform AbsorbHeat;
    }

    // ---------- Temperature Sensor ----------
    part def TemperatureSensor {
        port measurementPort : TempSensorPort;
        port mountingPort : CoolantInPort;

        attribute measuredTemp : TemperatureValue;
        attribute accuracy : TemperatureValue = 0.5;
        attribute samplingRate : RealValue { unit "Hz"; } = 10.0;

        action def MeasureTemperature {
            in coolant : Coolant;
            out temp : TemperatureValue;
            
            constraint { temp == coolant.currentTemp }
        }

        perform MeasureTemperature;
    }

    // ---------- Flow Valve ----------
    part def FlowValve {
        port coolantIn : CoolantInPort;
        port coolantOut : CoolantPort;
        port control : ValveControlPort;

        attribute position : ValvePositionValue;
        attribute maxFlowRate : FlowRateValue = 5.0;

        action def RegulateFlow {
            in coolantIn : CoolantInPort;
            out coolantOut : CoolantPort;
            in commandedPosition : ValvePositionValue;
            
            constraint { coolantOut.coolantFlow.flowRate == maxFlowRate * (commandedPosition / 100.0) }
            constraint { coolantOut.coolantFlow.currentTemp == coolantIn.coolantFlow.currentTemp }
        }

        perform RegulateFlow;
    }

    // ---------- Heat Exchanger ----------
    part def HeatExchanger {
        port coolantIn : CoolantInPort;
        port coolantOut : CoolantPort;

        attribute ambientTemp : TemperatureValue = 25.0;
        attribute heatTransferCoefficient : RealValue { unit "W/(m^2*K)"; } = 150.0;
        attribute surfaceArea : RealValue { unit "m^2"; } = 0.5;
        attribute coolingCapacity : HeatFluxValue;

        action def DissipateHeat {
            in coolantIn : CoolantInPort;
            out coolantOut : CoolantPort;
            
            attribute deltaT : TemperatureValue;
            
            constraint { coolantOut.coolantFlow.currentTemp == ambientTemp + (coolantIn.coolantFlow.currentTemp - ambientTemp) * 0.3 }
            constraint { coolingCapacity == heatTransferCoefficient * surfaceArea * (coolantIn.coolantFlow.currentTemp - ambientTemp) }
        }

        perform DissipateHeat;
    }

    // ---------- Cooling Controller ----------
    part def CoolingController {
        port sensorInput : TempSensorPort;
        port pumpControl : PumpControlPort;
        port valveControl : ValveControlPort;

        attribute currentTemp : TemperatureValue;
        attribute commandedPumpSpeed : SpeedValue;
        attribute commandedValvePosition : ValvePositionValue;
        attribute systemActive : Boolean = true;

        state def ControllerStates {
            entry; then Monitoring;

            state Monitoring {
                entry action {
                    commandedPumpSpeed = 0.0;
                    commandedValvePosition = 10.0;
                }
                transition Monitoring_CoolingActive first Monitoring
                    when (sensorInput.measuredTemp > targetTemp and sensorInput.measuredTemp <= maxCoolingThreshold)
                    then CoolingActive;
                transition Monitoring_MaxCooling first Monitoring
                    when (sensorInput.measuredTemp > maxCoolingThreshold and sensorInput.measuredTemp <= maxSafeTemp)
                    then MaxCooling;
                transition Monitoring_Shutdown first Monitoring
                    when (sensorInput.measuredTemp > maxSafeTemp)
                    then Shutdown;
            }

            state CoolingActive {
                entry action {
                    commandedPumpSpeed = 3000.0;
                    commandedValvePosition = 50.0;
                }
                transition CoolingActive_Monitoring first CoolingActive
                    when (sensorInput.measuredTemp <= targetTemp)
                    then Monitoring;
                transition CoolingActive_MaxCooling first CoolingActive
                    when (sensorInput.measuredTemp > maxCoolingThreshold)
                    then MaxCooling;
                transition CoolingActive_Shutdown first CoolingActive
                    when (sensorInput.measuredTemp > maxSafeTemp)
                    then Shutdown;
            }

            state MaxCooling {
                entry action {
                    commandedPumpSpeed = 5000.0;
                    commandedValvePosition = 100.0;
                }
                transition MaxCooling_CoolingActive first MaxCooling
                    when (sensorInput.measuredTemp <= maxCoolingThreshold and sensorInput.measuredTemp > targetTemp)
                    then CoolingActive;
                transition MaxCooling_Monitoring first MaxCooling
                    when (sensorInput.measuredTemp <= targetTemp)
                    then Monitoring;
                transition MaxCooling_Shutdown first MaxCooling
                    when (sensorInput.measuredTemp > maxSafeTemp)
                    then Shutdown;
            }

            state Shutdown {
                entry action {
                    commandedPumpSpeed = 0.0;
                    commandedValvePosition = 0.0;
                    systemActive = false;
                }
            }
        }

        part controllerStateMachine : ControllerStates;

        action def ProcessTemperature {
            in measuredTemp : TemperatureValue;
            out pumpCommand : SpeedValue;
            out valveCommand : ValvePositionValue;
            
            decision decideCoolingMode {
                if measuredTemp <= targetTemp then {
                    pumpCommand = 0.0;
                    valveCommand = 10.0;
                } else if measuredTemp <= maxCoolingThreshold then {
                    pumpCommand = 3000.0;
                    valveCommand = 50.0;
                } else if measuredTemp <= maxSafeTemp then {
                    pumpCommand = 5000.0;
                    valveCommand = 100.0;
                } else {
                    pumpCommand = 0.0;
                    valveCommand = 0.0;
                }
            }
        }

        perform ProcessTemperature;
    }

    // ---------- System Assembly ----------
    part def LiquidCoolingSystemAssembly {
        part pump : Pump;
        part heatSource : HeatSource;
        part tempSensor : TemperatureSensor;
        part flowValve : FlowValve;
        part heatExchanger : HeatExchanger;
        part controller : CoolingController;

        // Coolant flow connections (closed loop)
        connection coolantFlow1 connect pump.coolantOut to heatSource.coolantIn;
        connection coolantFlow2 connect heatSource.coolantOut to flowValve.coolantIn;
        connection coolantFlow3 connect flowValve.coolantOut to heatExchanger.coolantIn;
        connection coolantFlow4 connect heatExchanger.coolantOut to pump.coolantIn;

        // Sensor connection
        connection tempFeedback connect heatSource.sensorPort to controller.sensorInput;
        connection sensorMount connect heatSource.coolantIn to tempSensor.mountingPort;
        connection sensorOutput connect tempSensor.measurementPort to controller.sensorInput;

        // Control connections
        connection pumpControl connect controller.pumpControl to pump.control;
        connection valveControl connect controller.valveControl to flowValve.control;

        // Heat input
        port externalHeat : HeatInputPort;
        connection heatInput connect externalHeat to heatSource.heatInput;

        constraint closedLoopFlow {
            pump.coolantOut.coolantFlow.flowRate == heatSource.coolantIn.coolantFlow.flowRate and
            heatSource.coolantOut.coolantFlow.flowRate == flowValve.coolantIn.coolantFlow.flowRate and
            flowValve.coolantOut.coolantFlow.flowRate == heatExchanger.coolantIn.coolantFlow.flowRate and
            heatExchanger.coolantOut.coolantFlow.flowRate == pump.coolantIn.coolantFlow.flowRate
        }

        constraint thermalBalance {
            heatSource.heatInput.heatFlux == heatExchanger.coolingCapacity
        }
    }

    // ---------- Requirements ----------
    requirement def TemperatureControlRequirement {
        doc /* The system shall maintain the heat source temperature within safe operating limits. */
        attribute targetTemp : TemperatureValue = 45.0;
        attribute maxSafeTemp : TemperatureValue = 85.0;
        
        constraint { heatSource.surfaceTemp <= maxSafeTemp }
        constraint { heatSource.surfaceTemp >= targetTemp - 5.0 implies controller.commandedPumpSpeed > 0.0 }
    }

    requirement def PumpSpeedControlRequirement {
        doc /* The pump shall support standby, normal, and high-speed operating modes. */
        attribute standbySpeed : SpeedValue = 0.0;
        attribute normalSpeed : SpeedValue = 3000.0;
        attribute highSpeed : SpeedValue = 5000.0;
        
        constraint { pump.currentSpeed == standbySpeed or pump.currentSpeed == normalSpeed or pump.currentSpeed == highSpeed }
    }

    requirement def FlowRegulationRequirement {
        doc /* The flow valve shall regulate coolant flow rate between 0 and maximum. */
        attribute maxFlowRate : FlowRateValue = 5.0;
        
        constraint { flowValve.coolantOut.coolantFlow.flowRate >= 0.0 and flowValve.coolantOut.coolantFlow.flowRate <= maxFlowRate }
    }

    requirement def HeatDissipationRequirement {
        doc /* The heat exchanger shall dissipate heat to maintain thermal balance. */
        constraint { heatExchanger.coolingCapacity >= heatSource.heatInput.heatFlux }
    }

    requirement def ShutdownSafetyRequirement {
        doc /* The controller shall initiate shutdown when temperature exceeds the maximum safety limit. */
        constraint { controller.sensorInput.measuredTemp > maxSafeTemp implies controller.systemActive == false }
    }

    requirement def ResponseTimeRequirement {
        doc /* The system shall respond to temperature changes within 2 seconds. */
        attribute maxResponseTime : RealValue { unit "s"; } = 2.0;
        constraint { controller.samplingRate >= 1.0 / maxResponseTime }
    }

    package SystemRequirements {
        requirement tempControlReq : TemperatureControlRequirement;
        requirement pumpSpeedReq : PumpSpeedControlRequirement;
        requirement flowRegReq : FlowRegulationRequirement;
        requirement heatDissReq : HeatDissipationRequirement;
        requirement shutdownReq : ShutdownSafetyRequirement;
        requirement responseTimeReq : ResponseTimeRequirement;
    }

    package SystemSatisfactions {
        satisfaction tempControlReq by LiquidCoolingSystemAssembly;
        satisfaction pumpSpeedReq by Pump;
        satisfaction flowRegReq by FlowValve;
        satisfaction heatDissReq by HeatExchanger;
        satisfaction shutdownReq by CoolingController;
        satisfaction responseTimeReq by CoolingController;
    }
}

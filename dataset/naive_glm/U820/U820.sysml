package PiezoelectricAccelerometerSystem {
    doc <<Complete model of a piezoelectric accelerometer system for measuring mechanical vibrations and acceleration.>>

    import ScalarValues::*;

    // ============================================================
    // UNIT DEFINITIONS
    // ============================================================

    unit m_per_s2;
    unit volt;
    unit coulomb;
    unit hertz;
    unit kelvin;
    unit second;
    unit ohm;
    unit farad;

    // ============================================================
    // VALUE TYPE DEFINITIONS
    // ============================================================

    value type Acceleration :> Real {
        unit m_per_s2;
    }

    value type VoltageValue :> Real {
        unit volt;
    }

    value type ChargeValue :> Real {
        unit coulomb;
    }

    value type FrequencyValue :> Real {
        unit hertz;
    }

    value type Temperature :> Real {
        unit kelvin;
    }

    value type TimeValue :> Real {
        unit second;
    }

    value type ImpedanceValue :> Real {
        unit ohm;
    }

    value type CapacitanceValue :> Real {
        unit farad;
    }

    value type DigitalCode :> Integer;

    value type PercentageValue :> Real;

    // ============================================================
    // ITEM DEFINITIONS
    // ============================================================

    item def MechanicalExcitation {
        doc <<Mechanical vibration and acceleration transmitted through the mounting base.>>
        attribute acceleration : Acceleration;
        attribute frequency : FrequencyValue;
        attribute timestamp : TimeValue;
    }

    item def ChargeSignal {
        doc <<Electrical charge signal generated by the piezoelectric crystal.>>
        attribute charge : ChargeValue;
        attribute timestamp : TimeValue;
        attribute temperature : Temperature;
    }

    item def VoltageSignal {
        doc <<Amplified analog voltage signal from the charge amplifier.>>
        attribute voltage : VoltageValue;
        attribute timestamp : TimeValue;
        attribute temperature : Temperature;
    }

    item def FilteredVoltageSignal {
        doc <<Filtered analog voltage signal with noise removed.>>
        attribute voltage : VoltageValue;
        attribute timestamp : TimeValue;
        attribute dominantFrequency : FrequencyValue;
    }

    item def DigitalSample {
        doc <<Discrete digital sample from the ADC.>>
        attribute code : DigitalCode;
        attribute timestamp : TimeValue;
        attribute sampleNumber : Integer;
    }

    item def AccelerationMeasurement {
        doc <<Final calibrated acceleration measurement output.>>
        attribute acceleration : Acceleration;
        attribute timestamp : TimeValue;
        attribute temperature : Temperature;
        attribute calibrationApplied : Boolean;
        attribute confidenceLevel : PercentageValue;
    }

    item def VibrationEvent {
        doc <<Detected vibration event triggering measurement.>>
        attribute detected : Boolean;
        attribute magnitude : Acceleration;
        attribute timestamp : TimeValue;
    }

    item def CalibrationData {
        doc <<Calibration data for the accelerometer.>>
        attribute calibrationFactor : Real;
        attribute offsetCorrection : VoltageValue;
        attribute temperatureCompensationSlope : Real;
        attribute referenceAcceleration : Acceleration;
        attribute calibrationTimestamp : TimeValue;
    }

    // ============================================================
    // PORT DEFINITIONS
    // ============================================================

    port def MechanicalInPort {
        in excitation : MechanicalExcitation;
    }

    port def MechanicalOutPort {
        out excitation : MechanicalExcitation;
    }

    port def ChargeOutPort {
        out chargeSignal : ChargeSignal;
    }

    port def ChargeInPort {
        in chargeSignal : ChargeSignal;
    }

    port def VoltageOutPort {
        out voltageSignal : VoltageSignal;
    }

    port def VoltageInPort {
        in voltageSignal : VoltageSignal;
    }

    port def FilteredVoltageOutPort {
        out filteredSignal : FilteredVoltageSignal;
    }

    port def FilteredVoltageInPort {
        in filteredSignal : FilteredVoltageSignal;
    }

    port def DigitalOutPort {
        out digitalSample : DigitalSample;
    }

    port def DigitalInPort {
        in digitalSample : DigitalSample;
    }

    port def MeasurementOutPort {
        out measurement : AccelerationMeasurement;
    }

    // ============================================================
    // ACTION DEFINITIONS
    // ============================================================

    action def PerformInitialization {
        doc <<Initialize all accelerometer subsystems upon power-on.>>
        attribute initializationDuration : TimeValue;

        action initializeChargeAmplifier;
        action initializeADC;
        action initializeSignalProcessor;
        action loadCalibrationData;
        action performSelfTest;

        first initializeChargeAmplifier then initializeADC;
        then initializeSignalProcessor then loadCalibrationData;
        then performSelfTest;
    }

    action def PerformCalibration {
        doc <<Calibrate the accelerometer against a known reference acceleration.>>
        attribute referenceAcceleration : Acceleration;
        attribute calibrationDuration : TimeValue;

        action applyReferenceAcceleration;
        action measureResponse;
        action computeCalibrationFactor;
        action computeTemperatureCompensation;
        action storeCalibrationData;

        first applyReferenceAcceleration then measureResponse;
        then computeCalibrationFactor then computeTemperatureCompensation;
        then storeCalibrationData;
    }

    action def PerformMeasurement {
        doc <<Perform continuous acceleration measurement and signal processing.>>

        action acquireChargeFromCrystal;
        action amplifyChargeSignal;
        action filterVoltageSignal;
        action convertToDigital;
        action applyCalibrationFactor;
        action applyTemperatureCompensation;
        action applyOffsetCorrection;
        action outputMeasurement;

        first acquireChargeFromCrystal then amplifyChargeSignal;
        then filterVoltageSignal then convertToDigital;
        then applyCalibrationFactor then applyTemperatureCompensation;
        then applyOffsetCorrection then outputMeasurement;
    }

    action def RaiseAlert {
        doc <<Raise an alert when measured vibration exceeds the threshold.>>
        attribute alertLevel : Integer;
        attribute alertTimestamp : TimeValue;
        attribute measuredAcceleration : Acceleration;

        action logAlertEvent;
        action setAlertFlag;
        action notifyHost;

        first logAlertEvent then setAlertFlag then notifyHost;
    }

    action def PerformShutdown {
        doc <<Safely shut down the accelerometer system.>>

        action stopMeasurement;
        action saveCurrentState;
        action powerDownComponents;

        first stopMeasurement then saveCurrentState then powerDownComponents;
    }

    // ============================================================
    // STATE MACHINE DEFINITION
    // ============================================================

    state def AccelerometerStateMachine {
        doc <<Operational state machine for the piezoelectric accelerometer system.>>

        attribute powerOnSignal : Boolean;
        attribute initializationComplete : Boolean;
        attribute calibrationCommand : Boolean;
        attribute calibrationComplete : Boolean;
        attribute vibrationDetected : Boolean;
        attribute vibrationThresholdExceeded : Boolean;
        attribute vibrationNormalized : Boolean;
        attribute stopMeasurementCommand : Boolean;
        attribute powerOffSignal : Boolean;
        attribute systemFaultDetected : Boolean;

        initial;

        state PowerOff {
            doc <<System is powered off and inactive.>>
        }

        state Initialization {
            doc <<System is initializing all subsystems after power-on.>>
            entry action initAction : PerformInitialization;
        }

        state Idle {
            doc <<System is idle and ready to measure or calibrate.>>
        }

        state Calibration {
            doc <<System is performing calibration against a known reference.>>
            entry action calibrateAction : PerformCalibration;
        }

        state Measuring {
            doc <<System is actively measuring acceleration and processing signals.>>
            entry action measureAction : PerformMeasurement;
        }

        state Alert {
            doc <<System has detected vibration exceeding the alert threshold.>>
            entry action alertAction : RaiseAlert;
        }

        state SystemShutdown {
            doc <<System has been shut down after a fault or explicit command.>>
            entry action shutdownAction : PerformShutdown;
        }

        transition from initial to PowerOff;
        transition from PowerOff to Initialization when powerOnSignal;
        transition from Initialization to Idle when initializationComplete;
        transition from Idle to Calibration when calibrationCommand;
        transition from Calibration to Idle when calibrationComplete;
        transition from Idle to Measuring when vibrationDetected;
        transition from Measuring to Alert when vibrationThresholdExceeded;
        transition from Alert to Measuring when vibrationNormalized;
        transition from Measuring to Idle when stopMeasurementCommand;
        transition from PowerOff to SystemShutdown when systemFaultDetected;
        transition from Idle to PowerOff when powerOffSignal;
        transition from Measuring to PowerOff when powerOffSignal;
        transition from Alert to PowerOff when powerOffSignal;
        transition from Calibration to PowerOff when powerOffSignal;
    }

    // ============================================================
    // PART DEFINITIONS — COMPONENTS
    // ============================================================

    part def MountingBase {
        doc <<Sturdy mounting base that physically connects the accelerometer to the measured object.>>

        attribute material : String = "Titanium";
        attribute youngsModulus : Real = 110;
        attribute mass : Real = 0.05;
        attribute mountingTorque : Real = 5;
        attribute maxOperatingTemperature : Temperature = 500;
        attribute thermalConductivity : Real = 7.4;

        port mechanicalIn : MechanicalInPort;
        port mechanicalOut : MechanicalOutPort;

        action transmitVibration {
            doc <<Transmit mechanical vibration from the mounting surface to the crystal.>>
        }
    }

    part def PiezoelectricCrystal {
        doc <<Piezoelectric crystal sensing element that converts mechanical stress to electrical charge.>>

        attribute crystalMaterial : String = "Quartz";
        attribute sensitivity : Real = 100;
        attribute capacitance : CapacitanceValue;
        attribute minOperatingTemperature : Temperature = 233;
        attribute maxOperatingTemperature : Temperature = 500;
        attribute chargeOutput : ChargeValue;
        attribute appliedAcceleration : Acceleration;

        constraint ChargeProportionality {
            doc <<Charge output is directly proportional to applied acceleration.>>
            chargeOutput == sensitivity * appliedAcceleration;
        }

        port mechanicalIn : MechanicalInPort;
        port chargeOut : ChargeOutPort;

        action generateCharge {
            doc <<Generate electrical charge proportional to applied mechanical stress.>>
        }
    }

    part def ChargeAmplifier {
        doc <<Charge amplifier converting high-impedance charge signal to low-impedance voltage.>>

        attribute gain : Real = 1000;
        attribute inputImpedance : ImpedanceValue;
        attribute outputImpedance : ImpedanceValue;
        attribute bandwidth : FrequencyValue;
        attribute noiseLevel : VoltageValue;
        attribute supplyVoltage : VoltageValue;

        port chargeIn : ChargeInPort;
        port voltageOut : VoltageOutPort;

        action amplifyCharge {
            doc <<Convert charge signal to amplified voltage signal.>>
        }
    }

    part def SignalFilter {
        doc <<Signal filter that removes irrelevant frequencies and electrical noise.>>

        attribute filterType : String = "Bandpass";
        attribute lowerCutoffFrequency : FrequencyValue;
        attribute upperCutoffFrequency : FrequencyValue;
        attribute filterOrder : Integer = 4;
        attribute passbandRipple : Real = 0.5;
        attribute stopbandAttenuation : Real = 40;

        port voltageIn : VoltageInPort;
        port filteredVoltageOut : FilteredVoltageOutPort;

        action filterSignal {
            doc <<Apply frequency-domain filtering to the voltage signal.>>
        }
    }

    part def AnalogDigitalConverter {
        doc <<Analog-to-digital converter sampling the filtered voltage at high rate.>>

        attribute sampleRate : FrequencyValue;
        attribute resolutionBits : Integer = 16;
        attribute inputVoltageRange : VoltageValue;
        attribute referenceVoltage : VoltageValue;
        attribute signalToNoiseRatio : Real;

        port analogIn : FilteredVoltageInPort;
        port digitalOut : DigitalOut

package PiezoelectricSensingUnitModel {
    import ScalarValues::*;

    // =========================================================
    // Value Types (with units)
    // =========================================================
    value type ForceMeasure :> Real {
        doc /* Force applied to the sensor element, expressed in newtons (N). */
    }
    value type PressureMeasure :> Real {
        doc /* Pressure acting on the sensing diaphragm, expressed in pascals (Pa). */
    }
    value type ChargeMeasure :> Real {
        doc /* Electric charge generated by the piezoelectric crystal, expressed in picocoulombs (pC). */
    }
    value type VoltageMeasure :> Real {
        doc /* Analog voltage, expressed in volts (V). */
    }
    value type CurrentMeasure :> Real {
        doc /* Supply current, expressed in milliamperes (mA). */
    }
    value type FrequencyMeasure :> Real {
        doc /* Frequency, expressed in hertz (Hz). */
    }
    value type TimeStampMeasure :> Real {
        doc /* Time stamp from boot, expressed in milliseconds (ms). */
    }
    value type PressureReading :> Real {
        doc /* Computed pressure value transmitted to the host, expressed in kilopascals (kPa). */
    }

    // =========================================================
    // Item Definitions
    // =========================================================
    item def ChargeSignal {
        attribute value : ChargeMeasure;
        attribute valid : Boolean;
    }
    item def VoltageSignal {
        attribute value : VoltageMeasure;
        attribute noiseFloor : VoltageMeasure;
        attribute valid : Boolean;
    }
    item def FilteredVoltageSignal {
        attribute value : VoltageMeasure;
        attribute cutoff : FrequencyMeasure;
        attribute valid : Boolean;
    }
    item def DigitalSample {
        attribute rawCount : Integer;
        attribute pressure : PressureReading;
        attribute timestamp : TimeStampMeasure;
        attribute sampleSequence : Integer;
        attribute valid : Boolean;
    }
    item def FaultReport {
        attribute faultCode : Integer;
        attribute description : String;
        attribute timestamp : TimeStampMeasure;
    }
    item def PowerSupplyInput {
        attribute voltage : VoltageMeasure;
        attribute maxCurrent : CurrentMeasure;
        attribute stable : Boolean;
    }

    // =========================================================
    // Port Definitions
    // =========================================================
    port def MechanicalPressurePort {
        in attribute appliedForce : ForceMeasure;
        in attribute appliedPressure : PressureMeasure;
    }
    port def ChargeFlowPort {
        attribute value : ChargeMeasure;
        attribute valid : Boolean;
    }
    port def VoltageFlowPort {
        attribute value : VoltageMeasure;
        attribute valid : Boolean;
    }
    port def FilteredFlowPort {
        attribute value : VoltageMeasure;
        attribute cutoff : FrequencyMeasure;
        attribute valid : Boolean;
    }
    port def DigitalDataPort {
        out attribute sample : DigitalSample;
        out attribute fault : FaultReport [0..*];
    }
    port def PowerPort {
        in attribute supply : PowerSupplyInput;
    }

    // =========================================================
    // Action Definitions
    // =========================================================
    action def SelfTest {
        out result : Boolean;
        out faultCode : Integer;
    }
    action def Diagnostics {
        out faults : FaultReport [0..*];
    }

    // =========================================================
    // Part Definitions
    // =========================================================
    part def PiezoelectricSensor {
        attribute material : String = "PZT-5H";
        attribute chargeCoeff : Real = 600.0;        // pC/N
        attribute maxForce : ForceMeasure = 5000.0;  // N
        attribute maxPressure : PressureMeasure = 50.0e6; // Pa
        attribute temperatureRating : Real = 80.0;   // °C operating limit

        port mechanicalPort : MechanicalPressurePort;
        port chargeOut : ChargeFlowPort;

        action def Sense {
            in force : ForceMeasure;
            in pressure : PressureMeasure;
            out charge : ChargeMeasure;
            doc /* Converts applied mechanical stress to electrical charge Q = chargeCoeff * force. */
        }

        perform action sense : Sense {
            in force = mechanicalPort.appliedForce;
            in pressure = mechanicalPort.appliedPressure;
            out charge = chargeOut.value;
        }
    }

    part def ChargeAmplifier {
        attribute gain : Real = 1000.0;
        attribute outputRange : VoltageMeasure = 10.0;
        attribute inputBias : ChargeMeasure = 1.0;

        port powerIn : PowerPort;
        port chargeIn : ChargeFlowPort;
        port voltOut : VoltageFlowPort;

        action def Amplify {
            in charge : ChargeMeasure;
            out voltage : VoltageMeasure;
            doc /* Produces V = (charge * gain) / chargeScale, clamped to outputRange. */
        }

        perform action amplify : Amplify {
            in charge = chargeIn.value;
            out voltage = voltOut.value;
        }
    }

    part def SignalConditioner {
        attribute cutoffFreq : FrequencyMeasure = 5000.0;
        attribute order : Integer = 4;
        attribute filterType : String = "ButterworthLowPass";

        port voltIn : VoltageFlowPort;
        port filteredOut : FilteredFlowPort;

        action def Condition {
            in voltageIn : VoltageMeasure;
            out voltageOut : VoltageMeasure;
            doc /* Applies a low-pass filter at cutoffFreq to remove high-frequency noise. */
        }

        perform action condition : Condition {
            in voltageIn = voltIn.value;
            out voltageOut = filteredOut.value;
        }
    }

    part def AnalogToDigitalConverter {
        attribute resolution : Integer = 16;
        attribute sampleRate : FrequencyMeasure = 100000.0; // Hz
        attribute referenceVoltage : VoltageMeasure = 10.0;
        attribute conversionLatency : TimeStampMeasure = 0.01;

        port analogIn : FilteredFlowPort;
        port digitalOut : DigitalDataPort;

        action def Convert {
            in voltage : VoltageMeasure;
            in timestamp : TimeStampMeasure;
            out sample : DigitalSample;
            doc /* Samples voltage at sampleRate, converts to a 16-bit count, computes pressure. */
        }

        perform action convert : Convert {
            in voltage = analogIn.value;
            in timestamp : TimeStampMeasure = 0.0;
            out sample = digitalOut.sample;
        }
    }

    part def PowerSupply {
        attribute nominalVoltage : VoltageMeasure = 12.0;
        attribute maxCurrent : CurrentMeasure = 500.0;
        attribute regulated : Boolean = true;

        port powerOut : PowerPort;
    }

    // =========================================================
    // State Machine Definition
    // =========================================================
    state def OperatingStateMachine {
        entry; then Initializing;

        state Initializing {
            entry;
            do { perform selfTest : SelfTest; }
            transition to Operational [selfTest.result == true];
            transition to Fault [selfTest.result == false];
        }

        state Operational {
            entry;
            state Sensing;
            state Amplifying;
            state Conditioning;
            state Converting;
            state Outputting;

            transition Sensing to Amplifying;
            transition Amplifying to Conditioning;
            transition Conditioning to Converting;
            transition Converting to Outputting;
            transition Outputting to Sensing;

            transition to Fault [faultDetected == true];
        }

        state Fault {
            entry;
            do { perform diagnostics : Diagnostics; }
            transition to Initializing [restartRequested == true];
        }
    }

    // =========================================================
    // Composite Part Definition - Piezoelectric Sensing Unit
    // =========================================================
    part def PiezoelectricSensingUnit {
        attribute unitId : String;
        attribute firmwareVersion : String = "1.4.0";
        attribute samplingEnabled : Boolean = true;

        port mechanicalPort : MechanicalPressurePort;
        port powerPort : PowerPort;
        port dataPort : DigitalDataPort;

        part sensor : PiezoelectricSensor {
            port chargeOut : ChargeFlowPort;
        }
        part amplifier : ChargeAmplifier {
            port chargeIn : ChargeFlowPort;
            port voltOut : VoltageFlowPort;
            port powerIn : PowerPort;
        }
        part conditioner : SignalConditioner {
            port voltIn : VoltageFlowPort;
            port filteredOut : FilteredFlowPort;
        }
        part adc : AnalogToDigitalConverter {
            port analogIn : FilteredFlowPort;
            port digitalOut : DigitalDataPort;
        }
        part power : PowerSupply {
            port powerOut : PowerPort;
        }

        // Mechanical input flows to the sensor
        connect mechanicalPort to sensor.mechanicalPort;

        // Charge produced by the sensor feeds the amplifier
        connect sensor.chargeOut to amplifier.chargeIn;

        // Amplified voltage passes through the signal conditioner
        connect amplifier.voltOut to conditioner.voltIn;

        // Cleaned analog signal reaches the ADC
        connect conditioner.filteredOut to adc.analogIn;

        // ADC digital output is exposed on the unit's data port
        connect adc.digitalOut to dataPort;

        // Power supply routes regulated power to the amplifier
        connect power.powerOut to amplifier.powerIn;

        // Aggregate the operating state machine
        state operatingBehavior : OperatingStateMachine;
    }

    // =========================================================
    // Requirements
    // =========================================================
    requirement def FunctionalRequirement {
        doc /* Base class for functional requirements. */
    }
    requirement def PerformanceRequirement {
        doc /* Base class for performance requirements. */
    }
    requirement def ReliabilityRequirement {
        doc /* Base class for reliability requirements. */
    }

    requirement def MeasurePressureRequirement :> FunctionalRequirement {
        doc /* The unit shall measure an applied mechanical pressure and produce a corresponding digital reading. */
        subject unit : PiezoelectricSensingUnit;
        assumption appliedPressure >= 0.0;
        assumption appliedPressure <= 50.0e6;
        requirement outputPressure : PressureReading;
    }

    requirement def CrystalMaterialRequirement :> FunctionalRequirement {
        doc /* The sensor element shall be constructed from PZT-5H piezoelectric ceramic. */
        subject sensor : PiezoelectricSensor;
        requirement sensor.material == "PZT-5H";
    }

    requirement def ChargeGenerationRequirement :> FunctionalRequirement {
        doc /* The crystal shall generate an electric charge directly proportional to the applied force. */
        subject sensor : PiezoelectricSensor;
        requirement sensor.chargeCoeff == 600.0;
    }

    requirement def AmplificationRequirement :> FunctionalRequirement {
        doc /* A charge amplifier shall convert the weak charge signal into a robust analog voltage using an external power supply. */
        subject amplifier : ChargeAmplifier;
        requirement amplifier.gain == 1000.0;
        requirement amplifier.outputRange == 10.0;
    }

    requirement def FilteringRequirement :> FunctionalRequirement {
        doc /* A signal conditioner shall apply a low-pass filter to remove noise and interference outside the relevant frequency range. */
        subject conditioner : SignalConditioner;
        requirement conditioner.filterType == "ButterworthLowPass";
        requirement conditioner.cutoffFreq == 5000.0;
    }

    requirement def ConversionResolutionRequirement :> PerformanceRequirement {
        doc /* The ADC shall sample the conditioned analog voltage and produce a 16-bit digital reading. */
        subject adc : AnalogToDigitalConverter;
        requirement adc.resolution == 16;
        requirement adc.sampleRate == 100000.0;
    }

    requirement def OutputContentRequirement :> FunctionalRequirement {
        doc /* The digital output shall include the calculated pressure value and a timestamp. */
        subject unit : PiezoelectricSensingUnit;
        requirement unit.dataPort.sample.pressure.isDefined();
        requirement unit.dataPort.sample.timestamp.isDefined();
    }

    requirement def StateMachineRequirement :> ReliabilityRequirement {
        doc /* The unit shall operate through Initializing, SelfTest, Operational sensing cycle, and Fault states for diagnostics. */
        subject unit : PiezoelectricSensingUnit;
        requirement unit.operatingBehavior.OperatingStateMachine.isDefined();
    }

    requirement def FaultReportingRequirement :> ReliabilityRequirement {
        doc /* On a detected fault the unit shall transition to a Fault state and emit diagnostic fault reports. */
        subject unit : PiezoelectricSensingUnit;
        requirement unit.dataPort.fault.isDefined();
    }

    // =========================================================
    // Requirement Satisfaction
    // =========================================================
    part def PiezoelectricSensingUnit {
        satisfy MeasurePressureRequirement;
        satisfy StateMachineRequirement;
        satisfy OutputContentRequirement;
        satisfy FaultReportingRequirement;
    }
    part def PiezoelectricSensor {
        satisfy CrystalMaterialRequirement;
        satisfy ChargeGenerationRequirement;
    }
    part def ChargeAmplifier {
        satisfy AmplificationRequirement;
    }
    part def SignalConditioner {
        satisfy FilteringRequirement;
    }
    part def AnalogToDigitalConverter {
        satisfy ConversionResolutionRequirement;
    }
}

package IntelligentTempSensor {

package ValueTypes {
import ScalarValues::*;

value type TemperatureValue :> Real {
doc /* Temperature in degrees Celsius */;
attribute unit : String = "°C";
}

value type VoltageValue :> Real {
doc /* Voltage in Volts */;
attribute unit : String = "V";
}

value type CurrentValue :> Real {
doc /* Current in Amperes */;
attribute unit : String = "A";
}

value type DigitalCountValue :> Integer {
doc /* Raw ADC digital count */;
}

value type QualityScoreValue :> Real {
doc /* Measurement quality score in [0.0, 1.0] */;
}

value type SamplingRateValue :> Real {
doc /* Sampling rate in Hertz */;
attribute unit : String = "Hz";
}

value type FrequencyValue :> Real {
doc /* Frequency in Hertz */;
attribute unit : String = "Hz";
}

value type GainValue :> Real {
doc /* Linear gain factor */;
}

value type CalibrationCoefficientValue :> Real {
doc /* Polynomial calibration coefficient */;
}

value type ElapsedTimeValue :> Real {
doc /* Elapsed time in seconds */;
attribute unit : String = "s";
}

value type PowerLevelValue :> Real {
doc /* Power supply voltage in Volts DC */;
attribute unit : String = "V";
}

value type ErrorCountValue :> Integer {
doc /* Count of accumulated errors */;
}

value type SensitivityValue :> Real {
doc /* Transducer sensitivity in Volts per Kelvin */;
attribute unit : String = "V/K";
}
}

package Items {

item def RawElectricalSignal {
doc /* Weak electrical signal generated by the transducer */;
attribute voltage : VoltageValue;
attribute current : CurrentValue;
}

item def ConditionedAnalogSignal {
doc /* Amplified and noise-filtered analog signal */;
attribute voltage : VoltageValue;
attribute noiseLevel : VoltageValue;
attribute gainApplied : GainValue;
}

item def DigitalSample {
doc /* Digitized representation of the conditioned analog signal */;
attribute count : DigitalCountValue;
attribute timestamp : ElapsedTimeValue;
}

item def ProcessedTemperature {
doc /* Final calibrated temperature with quality score and metadata */;
attribute value : TemperatureValue;
attribute quality : QualityScoreValue;
attribute timestamp : ElapsedTimeValue;
attribute driftCompensationApplied : Boolean;
}

item def DiagnosticReport {
doc /* Detailed diagnostic report on sensor health and status */;
attribute status : DiagnosticStatusKind;
attribute driftValue : TemperatureValue;
attribute errorCount : ErrorCountValue;
attribute lastErrorCode : Integer;
attribute outOfRangeFlag : Boolean;
attribute uptime : ElapsedTimeValue;
}

item def CalibrationCommand {
doc /* Command to update calibration factors from external source */;
attribute referenceValue : TemperatureValue;
attribute coefficientSet : CalibrationCoefficientValue[3];
attribute applyNow : Boolean;
}

item def AdaptationParameters {
doc /* Parameters dynamically adjusting sampling rate and filter behavior */;
attribute targetSamplingRate : SamplingRateValue;
attribute filterCutoff : FrequencyValue;
attribute powerOptimize : Boolean;
}

item def PowerInputSignal {
doc /* Power supply input signal */;
attribute level : PowerLevelValue;
attribute stabilized : Boolean;
}

item def ModeSwitchCommand {
doc /* Command to change operating mode */;
attribute targetMode : OperatingModeKind;
}

enumeration def DiagnosticStatusKind {
enum NORMAL;
enum DEGRADED;
enum FAULTED;
enum CALIBRATION_WARNING;
enum SELF_TEST_IN_PROGRESS;
}

enumeration def OperatingModeKind {
enum INIT;
enum MEASURE;
enum DIAGNOSTIC;
enum FAULT;
}
}

package Ports {

port def PowerInputPort {
doc /* External power supply interface */;
in item power : PowerInputSignal;
}

port def CalibrationPort {
doc /* External calibration interface for factory or field calibration */;
in item command : CalibrationCommand;
}

port def MeasurementOutputPort {
doc /* Output for processed temperature measurement including value and quality score */;
out item reading : ProcessedTemperature;
}

port def DiagnosticOutputPort {
doc /* Output for detailed diagnostic report */;
out item report : DiagnosticReport;
}

port def OperatingModePort {
doc /* Mode control and current-mode feedback interface */;
in item modeCommand : ModeSwitchCommand;
out item currentMode : OperatingModeKind;
}

port def RawSignalOutPort {
out item raw : RawElectricalSignal;
}

port def RawSignalInPort {
in item raw : RawElectricalSignal;
}

port def ConditionedSignalOutPort {
out item conditioned : ConditionedAnalogSignal;
}

port def ConditionedSignalInPort {
in item conditioned : ConditionedAnalogSignal;
}

port def DigitalSampleOutPort {
out item digital : DigitalSample;
}

port def DigitalSampleInPort {
in item digital : DigitalSample;
}

port def ProcessedTemperatureOutPort {
out item processed : ProcessedTemperature;
}

port def ProcessedTemperatureInPort {
in item processed : ProcessedTemperature;
}

port def DiagnosticReportOutPort {
out item report : DiagnosticReport;
}

port def AdaptationParametersOutPort {
out item parameters : AdaptationParameters;
}

port def AdaptationParametersInPort {
in item parameters : AdaptationParameters;
}
}

package Behaviors {
import ValueTypes::*;
import Items::*;

action def initializationSequence {
doc /* Initialize all subsystems, load calibration tables and configuration */;
out success : Boolean;
}

action def selfTest {
doc /* Run self-test covering transducer, conditioner, ADC, microprocessor, diagnostics, and adaptation */;
in powerAvailable : Boolean;
out selfTestPassed : Boolean;
out selfTestFailed : Boolean;
out failingModule : String;
}

action def acquire {
doc /* Acquire a raw temperature sample through the transducer chain */;
out sample : DigitalSample;
}

action def processMeasurement {
doc /* Apply calibration coefficients, nonlinearity compensation, and quality scoring */;
in rawSample : DigitalSample;
out processed : ProcessedTemperature;
}

action def validateAndOutput {
doc /* Validate range, finalize quality score, and emit the processed temperature */;
in processed : ProcessedTemperature;
out validated : ProcessedTemperature;
}

action def runDiagnostics {
doc /* Run extended diagnostics including drift detection and range validation */;
out report : DiagnosticReport;
}

action def logFault {
doc /* Record fault details, set fault status, and emit faulted diagnostic report */;
in errorCode : Integer;
out report : DiagnosticReport;
}

state def SensorLifecycleStateMachine {
doc /* Well-defined lifecycle: initialization and self-test, measuring, diagnostic, fault handling */;

attribute selfTestPassed : Boolean;
attribute selfTestFailed : Boolean;
attribute measurementRequested : Boolean;
attribute measurementComplete : Boolean;
attribute criticalErrorDetected : Boolean;
attribute diagnosticRequested : Boolean;
attribute diagnosticComplete : Boolean;
attribute resetCommandReceived : Boolean;

initial start;
state Initializing {
doc /* Boot-up, configuration load, and self-test sequence */;
entry initializationSequence;
do selfTest;
}
state Ready {
doc /* Operational and idle, awaiting measurement or diagnostic command */;
}
state Measuring {
doc /* Acquire, process, validate, and output a temperature reading */;
entry acquire;
do processMeasurement;
exit validateAndOutput;
}
state Diagnostic {
doc /* Dedicated diagnostic mode for troubleshooting */;
entry runDiagnostics;
}
state Fault {
doc /* Critical failure state with fault logging */;
entry logFault;
}

transition start to Initializing;
transition Initializing to Ready when selfTestPassed;
transition Initializing to Fault when selfTestFailed;
transition Ready to Measuring when measurementRequested;
transition Measuring to Ready when measurementComplete;
transition Measuring to Fault when criticalErrorDetected;
transition Ready to Diagnostic when diagnosticRequested;
transition Diagnostic to Ready when diagnosticComplete;
transition Fault to Initializing when resetCommandReceived;
}
}

package Components {
import ValueTypes::*;
import Items::*;
import Ports::*;
import Behaviors::*;

part def TemperatureTransducer {
doc /* Transducer element that converts physical temperature into a raw electrical signal */;
attribute sensitivity : SensitivityValue = 0.01;
attribute responseTime : ElapsedTimeValue = 0.5;
attribute operatingMin : TemperatureValue = -55.0;
attribute operatingMax : TemperatureValue = 125.0;
port rawOut : RawSignalOutPort;
action transduce {
in physicalTemperature : TemperatureValue;
out signal : RawElectricalSignal;
}
}

part def SignalConditioner {
doc /* Amplifies and filters the raw transducer signal to produce a cleaner, stable analog signal */;
attribute gain : GainValue = 100.0;
attribute cutoffFrequency : FrequencyValue = 100.0;
port rawIn : RawSignalInPort;
port conditionedOut : ConditionedSignalOutPort;
port paramsIn : AdaptationParametersInPort;
action condition {
in input : RawElectricalSignal;
in filterCutoff : FrequencyValue;
in gainSetting : GainValue;
out output : ConditionedAnalogSignal;
}
}

part def ADC {
doc /* Analog-to-digital converter transforming the conditioned analog signal into digital format */;
attribute resolutionBits : Integer = 16;
attribute maxSamplingRate : SamplingRateValue = 1000.0;
attribute currentSamplingRate : SamplingRateValue = 10.0;
port conditionedIn : ConditionedSignalInPort;
port digitalOut : DigitalSampleOutPort;
port paramsIn : AdaptationParametersInPort;
action convert {
in input : ConditionedAnalogSignal;
in samplingRate : SamplingRateValue;
out output : DigitalSample;
}
}

part def MicroprocessorUnit {
doc /* Sensor brain: applies calibration factors, compensates nonlinearity, computes quality score */;
attribute calibrationCoefficients : CalibrationCoefficientValue[3] = (1.0, 0.0, 0.0);
attribute linearizationTableSize : Integer = 64;
attribute noiseEstimate : VoltageValue = 0.0;
port digitalIn : DigitalSampleInPort;
port processedOut : ProcessedTemperatureOutPort;
action process {
in input : DigitalSample;
out output : ProcessedTemperature;
}
action applyCalibration {
in raw : DigitalSample;
in coefficients : CalibrationCoefficientValue[3];
out calibrated : TemperatureValue;
}
action compensateNonlinearity {
in raw : TemperatureValue;
out compensated : TemperatureValue;
}
action computeQuality {
in measurement : TemperatureValue;
in noiseLevel : VoltageValue;
out score : QualityScoreValue;
}
}

part def SelfDiagnosticUnit {
doc /* Continuously monitors sensor health: drift detection, range validation, status and error reporting */;
attribute driftThreshold : TemperatureValue = 0.5;
attribute inRangeMin : TemperatureValue = -55.0;
attribute inRangeMax : TemperatureValue = 125.0;
attribute accumulatedErrorCount : ErrorCountValue = 0;
attribute lastErrorCode : Integer = 0;
port processedIn : ProcessedTemperatureInPort;
port reportOut : DiagnosticReportOutPort;
action monitor {
in measurement : ProcessedTemperature;
out report : DiagnosticReport;
}
action detectDrift {
in referenceHistory : ProcessedTemperature[*];
out driftDetected : Boolean;
out driftValue : TemperatureValue;
}
action validateRange {
in value : TemperatureValue;
in min : TemperatureValue;
in max : TemperatureValue;
out inRange : Boolean;
}
action emitStatus {
out status : DiagnosticStatusKind;
out errorCount : ErrorCountValue;
}
}

part def AdaptiveAlgorithmModule {
doc /* Dynamically adjusts sampling rate and filter parameters to optimize quality or power consumption */;
attribute defaultSamplingRate : SamplingRateValue = 10.0;
attribute defaultFilterCutoff : FrequencyValue = 10.0;
attribute powerOptimizationEnabled : Boolean = false;
port processedIn : ProcessedTemperatureInPort;
port paramsOut : AdaptationParametersOutPort;
action adapt {
in currentQuality : QualityScoreValue;
in noiseLevel : VoltageValue;
in powerOptimize : Boolean;
out parameters : AdaptationParameters;
}
}
}

package TopLevel {
import ValueTypes::*;
import Items::*;
import Ports::*;
import Components::*;
import Behaviors::*;

part def IntelligentTempSensor {
doc /* Top-level intelligent, self-aware temperature sensing unit */;

port powerIn : PowerInputPort;
port calibrationIn : CalibrationPort;
port measurementOut : MeasurementOutputPort;
port diagnosticOut : DiagnosticOutputPort;
port modeInterface : OperatingModePort;

part transducer : TemperatureTransducer;
part conditioner : SignalConditioner;
part adc : ADC;
part micro : MicroprocessorUnit;
part diag : SelfDiagnosticUnit;
part adapt : AdaptiveAlgorithmModule;

connection transducer.rawOut to conditioner.rawIn;
connection conditioner.conditionedOut to adc.conditionedIn;
connection adc.digitalOut to micro.digitalIn;
connection micro.processedOut to diag.processedIn;
connection micro.processedOut to measurementOut;
connection micro.processedOut to adapt.processedIn;
connection diag.reportOut to diagnosticOut;
connection adapt.paramsOut to conditioner.paramsIn;
connection adapt.paramsOut to adc.paramsIn;

state lifecycle : SensorLifecycleStateMachine;
}
}

package Requirements {
import ScalarValues::*;
import ValueTypes::*;
import TopLevel::*;

requirement def SelfTestRequirement {
doc /* The sensor shall complete initialization and self-test within maxSelfTestDuration seconds of power-on. */;
subject sensor : IntelligentTempSensor;
attribute maxSelfTestDuration : ElapsedTimeValue = 5.0;
}

requirement def MeasurementQualityRequirement {
doc /* Each output measurement shall carry a quality score not less than minQuality. */;
subject sensor : IntelligentTempSensor;
attribute minQuality : QualityScoreValue = 0.8;
}

requirement def DiagnosticReportRequirement {
doc /* The sensor shall continuously provide a diagnostic report containing status, drift, error codes, and range validation. */;
subject sensor : IntelligentTempSensor;
}

requirement def AdaptiveOperationRequirement {
doc /* The sensor shall dynamically adjust its sampling rate and filter parameters to optimize measurement quality or power consumption. */;
subject sensor : IntelligentTempSensor;
}

requirement def FaultHandlingRequirement {
doc /* On critical failure the sensor shall enter the Fault state and emit a faulted diagnostic report. */;
subject sensor : IntelligentTempSensor;
}

requirement def DriftDetectionRequirement {
doc /* The sensor shall detect calibration drift exceeding driftThreshold and emit a calibration warning. */;
subject sensor : IntelligentTempSensor;
attribute driftThreshold : TemperatureValue = 0.5;
}

requirement def CalibrationInterfaceRequirement {
doc /* The sensor shall accept external calibration commands via the calibration port and apply updated coefficients. */;
subject sensor : IntelligentTempSensor;
}

requirement def TemperatureRangeRequirement {
doc /* The sensor shall measure temperatures accurately within its specified operating range. */;
subject sensor : IntelligentTempSensor;
attribute minTemp : TemperatureValue;
attribute maxTemp : TemperatureValue;
attribute maxError : TemperatureValue;
}

requirement def HighPrecisionRangeRequirement :> TemperatureRangeRequirement {
doc /* High-precision laboratory variant operating range and accuracy */;
attribute redefines minTemp = -40.0;
attribute redefines maxTemp = 85.0;
attribute redefines maxError = 0.05;
}

requirement def IndustrialRangeRequirement :> TemperatureRangeRequirement {
doc /* Rugged industrial variant operating range and accuracy */;
attribute redefines minTemp = -55.0;
attribute redefines maxTemp = 125.0;
attribute redefines maxError = 0.5;
}
}

package Configurations {
import ValueTypes::*;
import TopLevel::*;
import Requirements::*;

part def HighPrecisionLabSensor :> IntelligentTempSensor {
doc /* High-precision configuration for laboratory use */;
part redefines transducer {
attribute redefines sensitivity = 0.02;
attribute redefines operatingMin = -40.0;
attribute redefines operatingMax = 85.0;
}
part redefines conditioner {
attribute redefines gain = 200.0;
attribute redefines cutoffFrequency = 50.0;
}
part redefines adc {
attribute redefines resolutionBits = 24;
attribute redefines currentSamplingRate = 100.0;
}
part redefines micro {
attribute redefines linearizationTableSize = 256;
}
part redefines diag {
attribute redefines driftThreshold = 0.05;
}
}

part def RuggedIndustrialSensor :> IntelligentTempSensor {
doc /* Rugged configuration for industrial environments with wider operating range */;
part redefines transducer {
attribute redefines sensitivity = 0.005;
attribute redefines operatingMin = -55.0;
attribute redefines operatingMax = 125.0;
}
part redefines conditioner {
attribute redefines gain = 50.0;
attribute redefines cutoffFrequency = 20.0;
}
part redefines adc {
attribute redefines resolutionBits = 16;
attribute redefines currentSamplingRate = 5.0;
}
part redefines micro {
attribute redefines linearizationTableSize = 64;
}
part redefines diag {
attribute redefines driftThreshold = 1.0;
}
}

part highPrecisionInstance : HighPrecisionLabSensor;
part industrialInstance : RuggedIndustrialSensor;

requirement selfTestReq : SelfTestRequirement;
requirement qualityReq : MeasurementQualityRequirement;
requirement diagReq : DiagnosticReportRequirement;
requirement adaptReq : AdaptiveOperationRequirement;
requirement faultReq : FaultHandlingRequirement;
requirement driftReq : DriftDetectionRequirement;
requirement calibReq : CalibrationInterfaceRequirement;
requirement hprReq : HighPrecisionRangeRequirement;
requirement indReq : IndustrialRangeRequirement;

satisfy selfTestReq by highPrecisionInstance;
satisfy qualityReq by highPrecisionInstance;
satisfy diagReq by highPrecisionInstance;
satisfy adaptReq by highPrecisionInstance;
satisfy faultReq by highPrecisionInstance;
satisfy driftReq by highPrecisionInstance;
satisfy calibReq by highPrecisionInstance;
satisfy hprReq by highPrecisionInstance;

satisfy selfTestReq by industrialInstance;
satisfy qualityReq by industrialInstance;
satisfy diagReq by industrialInstance;
satisfy adaptReq by industrialInstance;
satisfy faultReq by industrialInstance;
satisfy driftReq by industrialInstance;
satisfy calibReq by industrialInstance;
satisfy indReq by industrialInstance;
}
}

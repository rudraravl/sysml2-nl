package 'Pinard Horn Fetal Auscultation System' {
    private import ScalarValues::*;
    private import ISQ::*;
    private import SI::*;

    attribute def HeartRateValue :> ISQ::FrequencyValue {
        doc /* Heart rate measured in beats per minute */
    }

    attribute def AcousticAmplificationFactor :> Real;

    item def AcousticSignal {
        attribute frequency : ISQ::FrequencyValue;
        attribute soundPressure : ISQ::PressureValue;
        attribute intensity : ISQ::PowerValue;
    }

    item def FetalHeartSound :> AcousticSignal {
        attribute heartRate : HeartRateValue;
        doc /* Acoustic signal generated by fetal cardiac activity */
    }

    item def AmplifiedSound :> AcousticSignal {
        attribute amplificationFactor : AcousticAmplificationFactor;
        doc /* Acoustically amplified sound suitable for human perception */
    }

    item def BeginExamination;
    item def HeartbeatDetected;
    item def SignalWeak;
    item def PositionAdjusted;
    item def MeasurementComplete;
    item def NewExamination;

    port def AcousticInputPort {
        in item inputSignal : AcousticSignal;
    }

    port def AcousticOutputPort {
        out item outputSignal : AcousticSignal;
    }

    part def BellComponent {
        attribute diameter : ISQ::LengthValue;
        attribute wallThickness : ISQ::LengthValue;
        attribute material : String;
        port contactSurface : AcousticInputPort;
        port internalOpening : AcousticOutputPort;

        action collectSound {
            in externalSound : AcousticSignal;
            out collectedSound : AcousticSignal;
            doc /* Captures sound waves from maternal abdomen surface */
        }
    }

    part def ResonatingTube {
        attribute length : ISQ::LengthValue;
        attribute innerDiameter : ISQ::LengthValue;
        attribute resonantFrequency : ISQ::FrequencyValue;
        port proximalEnd : AcousticInputPort;
        port distalEnd : AcousticOutputPort;

        action amplifyByResonance {
            in inputWave : AcousticSignal;
            out amplifiedWave : AmplifiedSound;
            doc /* Mechanically amplifies sound through acoustic resonance */
        }
    }

    part def EarpieceComponent {
        attribute openingDiameter : ISQ::LengthValue;
        attribute sealEfficiency : Real;
        port soundInput : AcousticInputPort;
        port auditoryOutput : AcousticOutputPort;

        action deliverToEar {
            in amplifiedSignal : AmplifiedSound;
            out auditorySignal : AmplifiedSound;
            doc /* Directs amplified sound into clinician's ear canal */
        }
    }

    part def PinardHorn {
        doc /* Trumpet-shaped passive acoustic stethoscope for fetal heart auscultation */

        attribute totalLength : ISQ::LengthValue;
        attribute mass : ISQ::MassValue;
        attribute constructionMaterial : String;

        part bell : BellComponent {
            attribute :>> diameter = 50.0[mm];
            attribute :>> wallThickness = 2.0[mm];
            attribute :>> material = "Aluminum";
        }

        part tube : ResonatingTube {
            attribute :>> length = 180.0[mm];
            attribute :>> innerDiameter = 20.0[mm];
            attribute :>> resonantFrequency = 2.5[Hz];
        }

        part earpiece : EarpieceComponent {
            attribute :>> openingDiameter = 25.0[mm];
            attribute :>> sealEfficiency = 0.85;
        }

        connection bellToTube connect bell.internalOpening to tube.proximalEnd;
        connection tubeToEarpiece connect tube.distalEnd to earpiece.soundInput;
    }

    part def MaternalAbdomen {
        attribute surfaceArea : ISQ::AreaValue;
        port acousticEmission : AcousticOutputPort;

        action emitFetalSound {
            out fetalSignal : FetalHeartSound;
            doc /* Transmits fetal heart sounds through abdominal wall */
        }
    }

    part def Clinician {
        attribute experienceLevel : String;
        port auditoryReception : AcousticInputPort;

        action perceiveHeartbeat {
            in receivedSound : AmplifiedSound;
            out detectedRate : HeartRateValue;
            doc /* Interprets amplified sound to determine fetal heart rate */
        }
    }

    action def PositionInstrument {
        in device : PinardHorn;
        in targetSite : MaternalAbdomen;
        out positioned : Boolean;
        doc /* Places bell firmly against maternal abdomen at optimal location */
    }

    action def ConductAcousticPath {
        in sourceSound : FetalHeartSound;
        in amplificationDevice : PinardHorn;
        out transmittedSound : AmplifiedSound;

        first start;
        then action capture {
            in fetalSound = sourceSound;
            out capturedSignal : AcousticSignal;
        }
        then action resonate {
            in inputSignal = capture.capturedSignal;
            out resonatedSignal : AmplifiedSound;
        }
        then action transmit {
            in amplifiedInput = resonate.resonatedSignal;
            out finalOutput : AmplifiedSound;
        }
        then assign transmittedSound := transmit.finalOutput;
        then done;
    }

    action def PerformFetalAuscultation {
        in maternalSubject : MaternalAbdomen;
        in auscultationDevice : PinardHorn;
        in examiner : Clinician;
        out measuredHeartRate : HeartRateValue;

        first start;
        then action position : PositionInstrument {
            in device = auscultationDevice;
            in targetSite = maternalSubject;
            out positioned;
        }
        then action conduct : ConductAcousticPath {
            in sourceSound;
            in amplificationDevice = auscultationDevice;
            out transmittedSound;
        }
        then action interpret {
            in receivedSound = conduct.transmittedSound;
            out heartRate : HeartRateValue;
        }
        then assign measuredHeartRate := interpret.heartRate;
        then done;
    }

    state def AuscultationProcedureStates {
        entry; then preparation;

        state preparation {
            doc /* Clinician prepares equipment and patient */
        }

        transition preparation_to_positioning
            first preparation
            accept beginExam : BeginExamination
            then positioning;

        state positioning {
            doc /* Locating optimal contact point on maternal abdomen */
            do action locateHeartbeat;
        }

        transition positioning_to_listening
            first positioning
            accept heartbeatFound : HeartbeatDetected
            then listening;

        transition positioning_to_repositioning
            first positioning
            accept weakSignal : SignalWeak
            then repositioning;

        state repositioning {
            doc /* Adjusting horn position to improve signal quality */
            do action adjustPosition;
        }

        transition repositioning_to_positioning
            first repositioning
            accept positionFixed : PositionAdjusted
            then positioning;

        state listening {
            doc /* Actively monitoring and counting fetal heartbeats */
            do action countBeats;
        }

        transition listening_to_complete
            first listening
            accept measurementDone : MeasurementComplete
            then complete;

        state complete {
            doc /* Examination finished, results recorded */
        }

        transition complete_to_preparation
            first complete
            accept nextExam : NewExamination
            then preparation;
    }

    part fetalAuscultationSystem {
        doc /* Complete system for non-invasive fetal heart rate monitoring using passive acoustic amplification */

        part horn : PinardHorn {
            attribute :>> totalLength = 200.0[mm];
            attribute :>> mass = 0.12[kg];
            attribute :>> constructionMaterial = "Medical Grade Aluminum";
        }

        part patient : MaternalAbdomen {
            attribute :>> surfaceArea = 0.08[m^2];
        }

        part practitioner : Clinician {
            attribute :>> experienceLevel = "Certified Midwife";
        }

        connection abdominalContact connect patient.acousticEmission to horn.bell.contactSurface;
        connection auditoryInterface connect horn.earpiece.auditoryOutput to practitioner.auditoryReception;

        perform action auscultation : PerformFetalAuscultation[*] ordered;

        exhibit state procedureFlow : AuscultationProcedureStates;
    }

    requirement <'PHR-FN-001'> primaryFunctionRequirement {
        doc /* The Pinard horn system shall enable non-invasive auscultation of fetal heart sounds 
               during pregnancy by passively amplifying acoustic signals through mechanical resonance 
               and transmitting them to the clinician's ear for interpretation and heart rate determination. */

        subject system : PinardHorn;

        require constraint {
            doc /* System must provide sufficient amplification for human perception */
            system.tube.resonantFrequency >= 2.0[Hz] and
            system.tube.resonantFrequency <= 3.0[Hz]
        }
    }

    requirement <'PHR-AC-001'> acousticAmplificationRequirement {
        doc /* The Pinard horn shall mechanically amplify fetal heart sounds within the frequency 
               range of 110-170 beats per minute without electronic components. */

        subject device : PinardHorn;

        require constraint {
            device.tube.length >= 150.0[mm] and
            device.tube.length <= 200.0[mm]
        }
    }

    requirement <'PHR-SF-001'> safetyRequirement {
        doc /* The Pinard horn shall be constructed from biocompatible, non-toxic materials 
               safe for direct contact with maternal skin. */

        subject instrument : PinardHorn;

        assume constraint {
            instrument.constructionMaterial == "Medical Grade Aluminum" or
            instrument.constructionMaterial == "Hardwood" or
            instrument.constructionMaterial == "Medical Grade Plastic"
        }
    }

    requirement <'PHR-US-001'> usabilityRequirement {
        doc /* The Pinard horn shall be lightweight and ergonomically designed for 
               extended clinical use without fatigue. */

        subject clinicalDevice : PinardHorn;

        require constraint {
            clinicalDevice.mass <= 0.15[kg]
        }
    }

    requirement <'PHR-PR-001'> performanceRequirement {
        doc /* The system shall enable detection of fetal heart rates in the normal range 
               of 110 to 170 beats per minute. */

        subject auscultationSystem;

        require constraint {
            doc /* Detectable heart rate range */
            110.0[1/min] <= 170.0[1/min]
        }
    }

    requirement systemLevelRequirement {
        doc /* The Pinard horn fetal auscultation system shall provide reliable, non-invasive 
               monitoring of fetal cardiac activity through passive acoustic amplification. */

        require primaryFunctionRequirement;
        require acousticAmplificationRequirement;
        require safetyRequirement;
        require usabilityRequirement;
        require performanceRequirement;
    }
}

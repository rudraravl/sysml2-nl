package CryogenicParticleDetectorSystem {

  import ScalarValues::*;
  import ISQ::*;
  import SI::*;

  attribute def Temperature {
    :>> unit = K;
  }

  attribute def Energy {
    :>> unit = J;
  }

  attribute def Voltage {
    :>> unit = V;
  }

  attribute def Current {
    :>> unit = A;
  }

  attribute def MagneticFluxDensity {
    :>> unit = T;
  }

  attribute def Pressure {
    :>> unit = Pa;
  }

  attribute def Time {
    :>> unit = s;
  }

  attribute def Frequency {
    :>> unit = Hz;
  }

  attribute def Power {
    :>> unit = W;
  }

  attribute def Length {
    :>> unit = m;
  }

  attribute def CountRate {
    :>> unit = Hz;
  }

  enum def ParticleKind {
    enum alpha;
    enum beta;
    enum gamma;
    enum neutron;
    enum xray;
    enum darkMatterCandidate;
    enum cosmicMuon;
    enum unknown;
  }

  item def ParticleEvent {
    attribute particleKind : ParticleKind;
    attribute depositedEnergy : Energy;
    attribute arrivalTime : Time;
    attribute interactionPositionX : Length;
    attribute interactionPositionY : Length;
    attribute interactionPositionZ : Length;
  }

  item def PhononSignal {
    attribute amplitude : Voltage;
    attribute riseTime : Time;
    attribute decayTime : Time;
    attribute sensorId : Integer;
  }

  item def ChargeSignal {
    attribute collectedCharge : Current;
    attribute driftTime : Time;
    attribute electrodeId : Integer;
  }

  item def DigitizedEvent {
    attribute eventId : Integer;
    attribute reconstructedEnergy : Energy;
    attribute timestamp : Time;
    attribute classification : ParticleKind;
    attribute confidence : Real;
    attribute valid : Boolean;
  }

  item def CryogenFlow {
    attribute massFlowRate : Real;
    attribute inletTemperature : Temperature;
    attribute outletTemperature : Temperature;
    attribute pressure : Pressure;
  }

  item def ControlCommand {
    attribute targetTemperature : Temperature;
    attribute detectorBiasVoltage : Voltage;
    attribute acquisitionEnabled : Boolean;
    attribute calibrationEnabled : Boolean;
  }

  item def HealthStatus {
    attribute coldStageTemperature : Temperature;
    attribute vacuumPressure : Pressure;
    attribute magnetField : MagneticFluxDensity;
    attribute electronicsTemperature : Temperature;
    attribute faultPresent : Boolean;
  }

  port def ParticleInputPort {
    in event : ParticleEvent;
  }

  port def ThermalPort {
    inout flow : CryogenFlow;
  }

  port def PhononSignalPort {
    out signal : PhononSignal;
  }

  port def ChargeSignalPort {
    out signal : ChargeSignal;
  }

  port def AnalogInputPort {
    in phonon : PhononSignal;
    in charge : ChargeSignal;
  }

  port def DigitalEventPort {
    out event : DigitizedEvent;
  }

  port def CommandPort {
    in command : ControlCommand;
  }

  port def StatusPort {
    out status : HealthStatus;
  }

  part def CryogenicParticleDetector {
    attribute nominalOperatingTemperature : Temperature = 0.015 [K];
    attribute maximumAllowedTemperature : Temperature = 0.080 [K];
    attribute minimumDetectableEnergy : Energy = 1.602e-17 [J];
    attribute maximumEventRate : CountRate = 1000 [Hz];

    port particleInput : ParticleInputPort;
    port commandInput : CommandPort;
    port statusOutput : StatusPort;
    port eventOutput : DigitalEventPort;

    part cryostat : DilutionRefrigerator;
    part detectorArray : DetectorArray;
    part magneticShield : MagneticShield;
    part vacuumSystem : VacuumSystem;
    part readoutElectronics : ReadoutElectronics;
    part eventProcessor : EventProcessor;
    part calibrationSystem : CalibrationSystem;
    part supervisoryController : SupervisoryController;

    connect cryostat.coldThermalInterface to detectorArray.thermalInterface;
    connect vacuumSystem.vacuumInterface to detectorArray.vacuumInterface;
    connect magneticShield.shieldedVolume to detectorArray.environmentInterface;

    connect particleInput.event to detectorArray.particleInput.event;
    connect detectorArray.phononOutput.signal to readoutElectronics.analogInput.phonon;
    connect detectorArray.chargeOutput.signal to readoutElectronics.analogInput.charge;
    connect readoutElectronics.rawEventOutput.event to eventProcessor.rawEventInput.event;
    connect eventProcessor.validatedEventOutput.event to eventOutput.event;

    connect commandInput.command to supervisoryController.commandInput.command;
    connect supervisoryController.cryogenicCommand.command to cryostat.commandInput.command;
    connect supervisoryController.biasCommand.command to readoutElectronics.commandInput.command;
    connect supervisoryController.calibrationCommand.command to calibrationSystem.commandInput.command;

    connect cryostat.statusOutput.status to supervisoryController.cryostatStatus.status;
    connect vacuumSystem.statusOutput.status to supervisoryController.vacuumStatus.status;
    connect readoutElectronics.statusOutput.status to supervisoryController.electronicsStatus.status;
    connect supervisoryController.systemStatus.status to statusOutput.status;

    perform primaryFunction : DetectCryogenicParticleEvents;
  }

  part def DetectorArray {
    attribute absorberMass : Real = 9.5;
    attribute numberOfDetectorModules : Integer = 128;
    attribute detectorPitch : Length = 0.025 [m];
    attribute biasVoltage : Voltage = 50 [V];

    port particleInput : ParticleInputPort;
    port thermalInterface : ThermalPort;
    port vacuumInterface : StatusPort;
    port environmentInterface : StatusPort;
    port phononOutput : PhononSignalPort;
    port chargeOutput : ChargeSignalPort;

    part modules[128] : DetectorModule;
  }

  part def DetectorModule {
    attribute operatingTemperature : Temperature = 0.015 [K];
    attribute absorberThickness : Length = 0.010 [m];
    attribute absorberDiameter : Length = 0.076 [m];

    part crystalAbsorber : CrystalAbsorber;
    part transitionEdgeSensors[4] : TransitionEdgeSensor;
    part chargeElectrodes[2] : ChargeElectrode;
    part thermalLink : WeakThermalLink;

    port particleInput : ParticleInputPort;
    port thermalInterface : ThermalPort;
    port phononOutput : PhononSignalPort;
    port chargeOutput : ChargeSignalPort;

    connect particleInput.event to crystalAbsorber.particleInput.event;
    connect crystalAbsorber.phononOutput.signal to transitionEdgeSensors.signalInput;
    connect crystalAbsorber.chargeOutput.signal to chargeElectrodes.signalInput;
    connect transitionEdgeSensors.signalOutput to phononOutput.signal;
    connect chargeElectrodes.signalOutput to chargeOutput.signal;
    connect thermalInterface.flow to thermalLink.coldBath.flow;
  }

  part def CrystalAbsorber {
    attribute material : String = "high-purity germanium";
    attribute heatCapacity : Real = 2.8e-12;
    attribute targetTemperature : Temperature = 0.015 [K];

    port particleInput : ParticleInputPort;
    port phononOutput : PhononSignalPort;
    port chargeOutput : ChargeSignalPort;

    action convertParticleEnergy {
      in particle : ParticleEvent;
      out phonon : PhononSignal;
      out charge : ChargeSignal;
    }
  }

  part def TransitionEdgeSensor {
    attribute transitionTemperature : Temperature = 0.020 [K];
    attribute normalResistance : Real = 0.120;
    attribute biasCurrent : Current = 8.0e-6 [A];
    attribute noiseEquivalentPower : Power = 2.0e-18 [W];

    in signalInput : PhononSignal;
    out signalOutput : PhononSignal;
  }

  part def ChargeElectrode {
    attribute electrodeBias : Voltage = 50 [V];
    attribute leakageCurrentLimit : Current = 1.0e-12 [A];

    in signalInput : ChargeSignal;
    out signalOutput : ChargeSignal;
  }

  part def WeakThermalLink {
    attribute thermalConductance : Real = 1.5e-9;

    port coldBath : ThermalPort;
  }

  part def DilutionRefrigerator {
    attribute baseTemperature : Temperature = 0.010 [K];
    attribute coolingPowerAt100mK : Power = 4.0e-4 [W];
    attribute heliumMixturePressure : Pressure = 85000 [Pa];

    port coldThermalInterface : ThermalPort;
    port commandInput : CommandPort;
    port statusOutput : StatusPort;

    part pulseTubeCooler : PulseTubeCooler;
    part stillStage : CryogenicStage;
    part mixingChamber : CryogenicStage;
    part temperatureController : TemperatureController;

    state def RefrigeratorState {
      state off;
      state cooldown;
      state stableOperation;
      state regeneration;
      state fault;

      initial then off;

      transition off_to_cooldown
        first off
        accept ControlCommand
        if command.acquisitionEnabled == true
        then cooldown;

      transition cooldown_to_stable
        first cooldown
        if mixingChamber.temperature <= 0.015 [K]
        then stableOperation;

      transition stable_to_regeneration
        first stableOperation
        if heliumMixturePressure < 60000 [Pa]
        then regeneration;

      transition any_to_fault
        first stableOperation
        if mixingChamber.temperature > 0.080 [K]
        then fault;
    }
  }

  part def PulseTubeCooler {
    attribute firstStageTemperature : Temperature = 45 [K];
    attribute secondStageTemperature : Temperature = 3.2 [K];
    attribute inputPower : Power = 7200 [W];
  }

  part def CryogenicStage {
    attribute temperature : Temperature;
    attribute coolingPower : Power;
    attribute thermalMass : Real;
  }

  part def TemperatureController {
    attribute proportionalGain : Real = 12.0;
    attribute integralGain : Real = 0.4;
    attribute heaterPowerLimit : Power = 2.0e-5 [W];

    action regulateTemperature {
      in measuredTemperature : Temperature;
      in setpoint : Temperature;
      out heaterPower : Power;
    }
  }

  part def VacuumSystem {
    attribute nominalPressure : Pressure = 1.0e-6 [Pa];
    attribute maximumPressure : Pressure = 1.0e-4 [Pa];

    port vacuumInterface : StatusPort;
    port statusOutput : StatusPort;

    part turbomolecularPump : VacuumPump;
    part ionPump : VacuumPump;
    part cryopanel : Cryopanel;
  }

  part def VacuumPump {
    attribute pumpingSpeed : Real;
    attribute operatingPower : Power;
  }

  part def Cryopanel {
    attribute surfaceTemperature : Temperature = 4 [K];
    attribute sorptionCapacity : Real = 0.15;
  }

  part def MagneticShield {
    attribute residualFieldLimit : MagneticFluxDensity = 1.0e-6 [T];
    attribute shieldingFactor : Real = 100000.0;

    port shieldedVolume : StatusPort;

    part outerMuMetalShield : ShieldLayer;
    part superconductingLeadShield : ShieldLayer;
  }

  part def ShieldLayer {
    attribute thickness : Length;
    attribute attenuationFactor : Real;
  }

  part def ReadoutElectronics {
    attribute samplingFrequency : Frequency = 2.0e6 [Hz];
    attribute adcResolutionBits : Integer = 18;
    attribute inputNoise : Voltage = 2.0e-9 [V];

    port analogInput : AnalogInputPort;
    port commandInput : CommandPort;
    port rawEventOutput : DigitalEventPort;
    port statusOutput : StatusPort;

    part squidAmplifiers[128] : SQUIDAmplifier;
    part analogFilters[128] : AntiAliasFilter;
    part digitizers[128] : Digitizer;

    action digitizeSignals {
      in phonon : PhononSignal;
      in charge : ChargeSignal;
      out rawEvent : DigitizedEvent;
    }
  }

  part def SQUIDAmplifier {
    attribute gain : Real = 5000.0;
    attribute bandwidth : Frequency = 500000 [Hz];
    attribute fluxNoise : Real = 3.0e-6;
  }

  part def AntiAliasFilter {
    attribute cutoffFrequency : Frequency = 250000 [Hz];
    attribute order : Integer = 6;
  }

  part def Digitizer {
    attribute sampleRate : Frequency = 2.0e6 [Hz];
    attribute resolutionBits : Integer = 18;
  }

  part def EventProcessor {
    attribute triggerThreshold : Energy = 1.602e-17 [J];
    attribute pileupRejectionWindow : Time = 0.002 [s];
    attribute classificationConfidenceMinimum : Real = 0.95;

    port rawEventInput : DigitalEventPort;
    port validatedEventOutput : DigitalEventPort;

    action reconstructEnergy {
      in rawEvent : DigitizedEvent;
      out calibratedEnergy : Energy;
    }

    action classifyEvent {
      in rawEvent : DigitizedEvent;
      in calibratedEnergy : Energy;
      out particleKind : ParticleKind;
      out confidence : Real;
    }

    action rejectNoiseAndPileup {
      in rawEvent : DigitizedEvent;
      out valid : Boolean;
    }

    state def ProcessingState {
      state idle;
      state armed;
      state triggered;
      state reconstructing;
      state publishing;

      initial then idle;

      transition idle_to_armed
        first idle
        accept ControlCommand
        if command.acquisitionEnabled == true
        then armed;

      transition armed_to_triggered
        first armed
        accept DigitizedEvent
        if event.reconstructedEnergy >= triggerThreshold
        then triggered;

      transition triggered_to_reconstructing
        first triggered
        then reconstructing;

      transition reconstructing_to_publishing
        first reconstructing
        if classificationConfidenceMinimum <= 0.95
        then publishing;

      transition publishing_to_armed
        first publishing
        then armed;
    }
  }

  part def CalibrationSystem {
    attribute calibrationInterval : Time = 3600 [s];
    attribute referenceXrayEnergy : Energy = 9.72e-16 [J];

    port commandInput : CommandPort;

    part sealedXraySource : CalibrationSource;
    part opticalPulser : OpticalPulser;

    action injectCalibrationEvent {
      out referenceEvent : ParticleEvent;
    }
  }

  part def CalibrationSource {
    attribute isotopeName : String = "Fe-55";
    attribute activity : Real = 37000.0;
    attribute emittedParticleKind : ParticleKind = ParticleKind::xray;
  }

  part def OpticalPulser {
    attribute wavelength : Length = 6.35e-7 [m];
    attribute pulseEnergy : Energy = 1.0e-15 [J];
    attribute repetitionRate : Frequency = 10 [Hz];
  }

  part def SupervisoryController {
    attribute nominalSetpoint : Temperature = 0.015 [K];
    attribute shutdownTemperature : Temperature = 0.080 [K];
    attribute shutdownPressure : Pressure = 1.0e-4 [Pa];

    port commandInput : CommandPort;
    port cryogenicCommand : CommandPort;
    port biasCommand : CommandPort;
    port calibrationCommand : CommandPort;
    port cryostatStatus : StatusPort;
    port vacuumStatus : StatusPort;
    port electronicsStatus : StatusPort;
    port systemStatus : StatusPort;

    action evaluateHealth {
      in cryostat : HealthStatus;
      in vacuum : HealthStatus;
      in electronics : HealthStatus;
      out system : HealthStatus;
    }

    action issueSafeShutdown {
      out command : ControlCommand;
    }
  }

  action def DetectCryogenicParticleEvents {
    in incomingParticle : ParticleEvent;
    out measuredEvent : DigitizedEvent;

    first start;
    then absorbEnergy;
    then generatePhononsAndCharge;
    then amplifyLowTemperatureSignals;
    then digitizeWaveforms;
    then reconstructAndClassifyEvent;
    then publishValidatedEvent;
    then done;

    action absorbEnergy {
      in particle : ParticleEvent;
      out depositedEnergy : Energy;
    }

    action generatePhononsAndCharge {
      in depositedEnergy : Energy;
      out phonon : PhononSignal;
      out charge : ChargeSignal;
    }

    action amplifyLowTemperatureSignals {
      in phonon : PhononSignal;
      in charge : ChargeSignal;
      out amplifiedPhonon : PhononSignal;
      out amplifiedCharge : ChargeSignal;
    }

    action digitizeWaveforms {
      in amplifiedPhonon : PhononSignal;
      in amplifiedCharge : ChargeSignal;
      out rawEvent : DigitizedEvent;
    }

    action reconstructAndClassifyEvent {
      in rawEvent : DigitizedEvent;
      out measuredEvent : DigitizedEvent;
    }

    action publishValidatedEvent {
      in measuredEvent : DigitizedEvent;
    }
  }

  requirement def PrimaryFunctionRequirement {
    doc /* The cryogenic particle detector system shall maintain an ultra-low-temperature detector array and convert individual particle interactions into validated digital events containing time, energy, and particle classification. */
    subject detector : CryogenicParticleDetector;

    require constraint {
      detector.detectorArray.numberOfDetectorModules >= 64
    }
  }

  requirement def OperatingTemperatureRequirement {
    doc /* The detector array shall operate at or below 15 mK during science acquisition to enable calorimetric measurement of minute particle energy depositions. */
    subject detector : CryogenicParticleDetector;

    require constraint {
      detector.cryostat.baseTemperature <= 0.015 [K]
    }
  }

  requirement def EnergyThresholdRequirement {
    doc /* The system shall detect particle interactions with deposited energy at or above 1.602e-17 J. */
    subject detector : CryogenicParticleDetector;

    require constraint {
      detector.minimumDetectableEnergy <= 1.602e-17 [J]
    }
  }

  requirement def VacuumRequirement {
    doc /* The detector payload shall be maintained below 1.0e-4 Pa to reduce convective heat transfer and contamination of cryogenic surfaces. */
    subject detector : CryogenicParticleDetector;

    require constraint {
      detector.vacuumSystem.maximumPressure <= 1.0e-4 [Pa]
    }
  }

  requirement def MagneticShieldingRequirement {
    doc /* The residual magnetic flux density at the detector array shall not exceed 1.0e-6 T to preserve transition-edge sensor stability. */
    subject detector : CryogenicParticleDetector;

    require constraint {
      detector.magneticShield.residualFieldLimit <= 1.0e-6 [T]
    }
  }

  requirement def EventThroughputRequirement {
    doc /* The acquisition and processing chain shall sustain a validated event throughput of 1000 events per second without data loss. */
    subject detector : CryogenicParticleDetector;

    require constraint {
      detector.maximumEventRate >= 1000 [Hz]
    }
  }

  requirement def SafeShutdownRequirement {
    doc /* The supervisory controller shall disable detector bias and acquisition if the cold stage exceeds 80 mK or the vacuum pressure exceeds 1.0e-4 Pa. */
    subject controller : SupervisoryController;

    require constraint {
      controller.shutdownTemperature == 0.080 [K]
    }

    require constraint {
      controller.shutdownPressure == 1.0e-4 [Pa]
    }
  }

  satisfy PrimaryFunctionRequirement by CryogenicParticleDetector;
  satisfy OperatingTemperatureRequirement by DilutionRefrigerator;
  satisfy EnergyThresholdRequirement by DetectorArray;
  satisfy VacuumRequirement by VacuumSystem;
  satisfy MagneticShieldingRequirement by MagneticShield;
  satisfy EventThroughputRequirement by ReadoutElectronics;
  satisfy SafeShutdownRequirement by SupervisoryController;
}

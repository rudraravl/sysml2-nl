package ArxivTransformerTextGenerationModel {

    import ScalarValues::*;

    item def TextPrompt {
        attribute characterCount : CharacterCount;
        attribute languageTag : LanguageTag;
    }

    item def GeneratedText {
        attribute characterCount : CharacterCount;
        attribute meanTokenConfidence : Probability;
    }

    item def TokenSequence {
        attribute tokenCount : TokenCount;
        attribute maxLength : TokenCount;
    }

    item def EmbeddingTensor {
        attribute tokenCount : TokenCount;
        attribute width : EmbeddingDimension;
    }

    item def AttentionTensor {
        attribute headCount : AttentionHeadCount;
        attribute sequenceLength : TokenCount;
    }

    item def ProbabilityDistribution {
        attribute vocabularySize : VocabularySize;
        attribute entropy : EntropyBits;
    }

    item def ModelWeights {
        attribute parameterCount : ParameterCount;
        attribute storageSize : DataSizeMiB;
    }

    item def UserIntent;

    attribute def TokenCount :> Integer;
    attribute def CharacterCount :> Integer;
    attribute def VocabularySize :> Integer;
    attribute def EmbeddingDimension :> Integer;
    attribute def AttentionHeadCount :> Integer;
    attribute def ParameterCount :> Integer;
    attribute def BatchSize :> Integer;
    attribute def Probability :> Real;
    attribute def EntropyBits :> Real;
    attribute def LatencyMs :> Real;
    attribute def ThroughputTokensPerSecond :> Real;
    attribute def DataSizeMiB :> Real;
    attribute def PowerW :> Real;
    attribute def Temperature :> Real;

    port def PromptInputPort {
        in item prompt : TextPrompt;
    }

    port def TextOutputPort {
        out item generatedText : GeneratedText;
    }

    port def TokenPort {
        inout item tokenSequence : TokenSequence;
    }

    port def EmbeddingPort {
        inout item embeddingTensor : EmbeddingTensor;
    }

    port def AttentionPort {
        inout item attentionTensor : AttentionTensor;
    }

    port def ProbabilityPort {
        out item distribution : ProbabilityDistribution;
    }

    port def WeightPort {
        in item weights : ModelWeights;
    }

    part def TransformerTextGenerationSystem {
        attribute arxivSourceId : String = "arXiv:1706.03762";
        attribute primaryFunction : String = "Generate coherent text by predicting next-token probability distributions using a stacked self-attention transformer architecture.";
        attribute maximumPromptTokens : TokenCount = 4096;
        attribute maximumGeneratedTokens : TokenCount = 1024;
        attribute nominalLatency : LatencyMs = 250.0;
        attribute nominalThroughput : ThroughputTokensPerSecond = 80.0;
        attribute nominalPower : PowerW = 450.0;

        port promptIn : PromptInputPort;
        port textOut : TextOutputPort;

        part tokenizer : Tokenizer;
        part embeddingStage : EmbeddingStage;
        part encoderDecoderCore : TransformerCore;
        part outputHead : OutputProjectionHead;
        part sampler : TokenSampler;
        part detokenizer : Detokenizer;
        part runtimeController : InferenceRuntimeController;

        connect promptIn to tokenizer.promptIn;
        connect tokenizer.tokensOut to embeddingStage.tokensIn;
        connect embeddingStage.embeddingsOut to encoderDecoderCore.embeddingsIn;
        connect encoderDecoderCore.contextOut to outputHead.contextIn;
        connect outputHead.probabilitiesOut to sampler.probabilitiesIn;
        connect sampler.tokensOut to detokenizer.tokensIn;
        connect detokenizer.textOut to textOut;

        perform action generateText : GenerateText;
        exhibit state lifecycle : InferenceLifecycle;
    }

    part def Tokenizer {
        attribute vocabularySize : VocabularySize = 50000;
        attribute averageCompressionRatio : Real = 3.8;

        port promptIn : PromptInputPort;
        port tokensOut : TokenPort;
    }

    part def EmbeddingStage {
        attribute embeddingWidth : EmbeddingDimension = 768;
        attribute positionalEncodingSupported : Boolean = true;

        port tokensIn : TokenPort;
        port embeddingsOut : EmbeddingPort;
        port weightsIn : WeightPort;
    }

    part def TransformerCore {
        attribute layerCount : Integer = 12;
        attribute attentionHeadsPerLayer : AttentionHeadCount = 12;
        attribute feedForwardWidth : EmbeddingDimension = 3072;
        attribute residualConnectionsEnabled : Boolean = true;
        attribute layerNormalizationEnabled : Boolean = true;

        port embeddingsIn : EmbeddingPort;
        port contextOut : EmbeddingPort;

        part layers[12] : TransformerLayer;
    }

    part def TransformerLayer {
        attribute hiddenWidth : EmbeddingDimension = 768;

        part multiHeadAttention : MultiHeadSelfAttention;
        part feedForwardNetwork : PositionWiseFeedForward;
        part firstNorm : LayerNormalization;
        part secondNorm : LayerNormalization;

        port layerIn : EmbeddingPort;
        port layerOut : EmbeddingPort;
    }

    part def MultiHeadSelfAttention {
        attribute headCount : AttentionHeadCount = 12;
        attribute keyWidth : EmbeddingDimension = 64;
        attribute valueWidth : EmbeddingDimension = 64;

        port queryKeyValueIn : EmbeddingPort;
        port attentionOut : AttentionPort;
    }

    part def PositionWiseFeedForward {
        attribute inputWidth : EmbeddingDimension = 768;
        attribute innerWidth : EmbeddingDimension = 3072;
        attribute activationFunction : String = "ReLU";

        port input : EmbeddingPort;
        port output : EmbeddingPort;
    }

    part def LayerNormalization {
        attribute epsilon : Real = 0.000001;

        port input : EmbeddingPort;
        port output : EmbeddingPort;
    }

    part def OutputProjectionHead {
        attribute vocabularySize : VocabularySize = 50000;

        port contextIn : EmbeddingPort;
        port probabilitiesOut : ProbabilityPort;
        port weightsIn : WeightPort;
    }

    part def TokenSampler {
        attribute temperature : Temperature = 0.8;
        attribute topK : Integer = 50;
        attribute topP : Probability = 0.95;

        port probabilitiesIn : ProbabilityPort;
        port tokensOut : TokenPort;
    }

    part def Detokenizer {
        port tokensIn : TokenPort;
        port textOut : TextOutputPort;
    }

    part def InferenceRuntimeController {
        attribute maximumBatchSize : BatchSize = 8;
        attribute timeoutLimit : LatencyMs = 5000.0;
        attribute cacheEnabled : Boolean = true;
    }

    action def GenerateText {
        in item prompt : TextPrompt;
        in item weights : ModelWeights;
        out item response : GeneratedText;

        action tokenizePrompt;
        action createEmbeddings;
        action applySelfAttentionLayers;
        action projectToVocabulary;
        action sampleNextTokens;
        action detokenizeResponse;

        first start;
        then tokenizePrompt;
        then createEmbeddings;
        then applySelfAttentionLayers;
        then projectToVocabulary;
        then sampleNextTokens;
        then detokenizeResponse;
        then done;
    }

    state def InferenceLifecycle {
        state idle;
        state validatingPrompt;
        state tokenizing;
        state runningTransformer;
        state sampling;
        state detokenizing;
        state returningResult;
        state faulted;

        transition initial then idle;
        transition idleToValidating first idle then validatingPrompt;
        transition validatingToTokenizing first validatingPrompt then tokenizing;
        transition tokenizingToRunning first tokenizing then runningTransformer;
        transition runningToSampling first runningTransformer then sampling;
        transition samplingToDetokenizing first sampling then detokenizing;
        transition detokenizingToReturning first detokenizing then returningResult;
        transition returningToIdle first returningResult then idle;

        transition validationFault first validatingPrompt then faulted;
        transition executionFault first runningTransformer then faulted;
        transition samplingFault first sampling then faulted;
        transition recover first faulted then idle;
    }

    requirement def PrimaryFunctionRequirement {
        subject system : TransformerTextGenerationSystem;
        doc /* The system shall transform a user prompt into generated natural-language text by computing context-aware next-token probabilities using transformer self-attention. */
    }

    requirement def ArxivBasisRequirement {
        subject system : TransformerTextGenerationSystem;
        doc /* The system architecture shall be based on the transformer model introduced in arXiv:1706.03762, using attention mechanisms as the primary sequence modeling operation. */
    }

    requirement def PromptCapacityRequirement {
        subject system : TransformerTextGenerationSystem;
        require constraint { system.maximumPromptTokens >= 4096 }
    }

    requirement def ThroughputRequirement {
        subject system : TransformerTextGenerationSystem;
        require constraint { system.nominalThroughput >= 50.0 }
    }

    requirement def LatencyRequirement {
        subject system : TransformerTextGenerationSystem;
        require constraint { system.nominalLatency <= 500.0 }
    }

    requirement def ConfidenceRequirement {
        subject output : GeneratedText;
        require constraint { output.meanTokenConfidence >= 0.50 }
    }

    part transformerTextGenerator : TransformerTextGenerationSystem;

    satisfy PrimaryFunctionRequirement by transformerTextGenerator;
    satisfy ArxivBasisRequirement by transformerTextGenerator;
    satisfy PromptCapacityRequirement by transformerTextGenerator;
    satisfy ThroughputRequirement by transformerTextGenerator;
    satisfy LatencyRequirement by transformerTextGenerator;
}

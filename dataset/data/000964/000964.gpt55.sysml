package ActinometerSystemModel {

	import ScalarValues::*;
	import SI::*;

	doc /* 
		Model of an actinometer system. The primary function of the system is to receive incident solar radiant energy through a calibrated aperture, convert the received radiation into an electrical measurement signal, compensate the signal for temperature and calibration effects, and provide a calibrated estimate of solar irradiance to a user or external data system.
	*/

	attribute def Irradiance {
		doc /* Radiant power incident per unit area. */
		:>> unit = "W/m^2";
		:>> quantityKind = "powerDensity";
	}

	attribute def RadiantPower {
		doc /* Total received radiant power. */
		:>> unit = "W";
		:>> quantityKind = "power";
	}

	attribute def ApertureArea {
		doc /* Effective optical receiving area. */
		:>> unit = "m^2";
		:>> quantityKind = "area";
	}

	attribute def Temperature {
		doc /* Thermodynamic temperature. */
		:>> unit = "degC";
		:>> quantityKind = "temperature";
	}

	attribute def Voltage {
		doc /* Electrical potential difference. */
		:>> unit = "V";
		:>> quantityKind = "electricPotential";
	}

	attribute def Current {
		doc /* Electrical current. */
		:>> unit = "A";
		:>> quantityKind = "electricCurrent";
	}

	attribute def Resistance {
		doc /* Electrical resistance. */
		:>> unit = "ohm";
		:>> quantityKind = "electricResistance";
	}

	attribute def TimeDuration {
		doc /* Duration of an interval. */
		:>> unit = "s";
		:>> quantityKind = "time";
	}

	attribute def Angle {
		doc /* Plane angle. */
		:>> unit = "deg";
		:>> quantityKind = "angle";
	}

	attribute def DimensionlessRatio {
		doc /* Ratio without physical dimension. */
		:>> unit = "1";
	}

	attribute def DigitalCount {
		doc /* Quantized digital sample count. */
		:>> unit = "count";
	}

	attribute def Energy {
		doc /* Accumulated radiant energy. */
		:>> unit = "J";
		:>> quantityKind = "energy";
	}

	attribute def DataRate {
		doc /* Rate of digital information transfer. */
		:>> unit = "bit/s";
		:>> quantityKind = "dataRate";
	}

	attribute def Power {
		doc /* Electrical power. */
		:>> unit = "W";
		:>> quantityKind = "power";
	}

	enum def OperatingMode {
		enum idle;
		enum darkReference;
		enum measuring;
		enum saturated;
		enum fault;
		enum maintenance;
	}

	enum def HealthStatus {
		enum healthy;
		enum degraded;
		enum failed;
	}

	enum def RadiationBand {
		enum broadbandSolar;
		enum ultraviolet;
		enum visible;
		enum infrared;
	}

	item def SolarRadiation {
		doc /* Incident electromagnetic radiation entering the actinometer aperture. */
		attribute irradiance : Irradiance;
		attribute band : RadiationBand = RadiationBand::broadbandSolar;
		attribute incidenceAngle : Angle;
	}

	item def FilteredRadiation {
		doc /* Radiation after aperture geometry, window transmission, and spectral filtering. */
		attribute irradiance : Irradiance;
		attribute transmittedPower : RadiantPower;
		attribute band : RadiationBand;
	}

	item def ThermalSignal {
		doc /* Thermal response generated by absorbed radiation. */
		attribute hotJunctionTemperature : Temperature;
		attribute coldJunctionTemperature : Temperature;
		attribute temperatureDifference : Temperature;
	}

	item def ElectricalSignal {
		doc /* Analog electrical signal proportional to absorbed radiation. */
		attribute voltage : Voltage;
		attribute current : Current;
		attribute sourceImpedance : Resistance;
	}

	item def DigitalSample {
		doc /* Digital representation of an analog measurement channel. */
		attribute rawCount : DigitalCount;
		attribute sampleTime : TimeDuration;
		attribute channelIdentifier : String;
	}

	item def CalibrationData {
		doc /* Calibration coefficients used to convert raw measurements into irradiance. */
		attribute responsivity : Voltage;
		attribute offsetVoltage : Voltage;
		attribute temperatureCoefficient : DimensionlessRatio;
		attribute apertureArea : ApertureArea;
		attribute validForBand : RadiationBand;
	}

	item def IrradianceReading {
		doc /* Calibrated actinometer output representing solar irradiance. */
		attribute irradiance : Irradiance;
		attribute uncertainty : Irradiance;
		attribute integrationTime : TimeDuration;
		attribute sensorTemperature : Temperature;
		attribute health : HealthStatus;
	}

	item def ElectricalPower {
		doc /* Electrical power supplied to system electronics. */
		attribute voltage : Voltage;
		attribute current : Current;
		attribute availablePower : Power;
	}

	item def Command {
		doc /* External user or host command. */
		attribute requestedMode : OperatingMode;
		attribute integrationTime : TimeDuration;
	}

	item def StatusMessage {
		doc /* Health and operating status reported by the actinometer. */
		attribute mode : OperatingMode;
		attribute health : HealthStatus;
		attribute sensorTemperature : Temperature;
		attribute lastReading : Irradiance;
	}

	port def RadiationInPort {
		in item radiation : SolarRadiation;
	}

	port def FilteredRadiationPort {
		out item radiation : FilteredRadiation;
	}

	port def FilteredRadiationInPort {
		in item radiation : FilteredRadiation;
	}

	port def ThermalSignalPort {
		out item signal : ThermalSignal;
	}

	port def ThermalSignalInPort {
		in item signal : ThermalSignal;
	}

	port def AnalogSignalPort {
		out item signal : ElectricalSignal;
	}

	port def AnalogSignalInPort {
		in item signal : ElectricalSignal;
	}

	port def DigitalSamplePort {
		out item sample : DigitalSample;
	}

	port def DigitalSampleInPort {
		in item sample : DigitalSample;
	}

	port def ReadingOutPort {
		out item reading : IrradianceReading;
	}

	port def ReadingInPort {
		in item reading : IrradianceReading;
	}

	port def CommandInPort {
		in item command : Command;
	}

	port def StatusOutPort {
		out item status : StatusMessage;
	}

	port def PowerInPort {
		in item power : ElectricalPower;
	}

	port def PowerOutPort {
		out item power : ElectricalPower;
	}

	port def CalibrationPort {
		out item calibration : CalibrationData;
	}

	port def CalibrationInPort {
		in item calibration : CalibrationData;
	}

	part def OpticalAperture {
		doc /* Defines the receiving geometry and admits incident solar radiation into the instrument. */

		attribute effectiveArea : ApertureArea = 1.000E-4 [m^2];
		attribute fieldOfView : Angle = 5.0 [deg];
		attribute windowTransmission : DimensionlessRatio = 0.92 [1];
		attribute cleanlinessFactor : DimensionlessRatio = 0.98 [1];

		port incident : RadiationInPort;
		port filtered : FilteredRadiationPort;

		action def LimitAndTransmitRadiation {
			in item inputRadiation : SolarRadiation;
			out item outputRadiation : FilteredRadiation;

			attribute acceptedIrradiance : Irradiance;
			attribute transmittedPower : RadiantPower;

			calc acceptedIrradiance = inputRadiation.irradiance * windowTransmission * cleanlinessFactor;
			calc transmittedPower = acceptedIrradiance * effectiveArea;
		}
	}

	part def SpectralFilter {
		doc /* Restricts the measurement band and attenuates out-of-band radiation. */

		attribute selectedBand : RadiationBand = RadiationBand::broadbandSolar;
		attribute inBandTransmission : DimensionlessRatio = 0.90 [1];
		attribute outOfBandRejection : DimensionlessRatio = 0.995 [1];

		port input : FilteredRadiationInPort;
		port output : FilteredRadiationPort;

		action def ApplySpectralResponse {
			in item incidentFilteredRadiation : FilteredRadiation;
			out item bandLimitedRadiation : FilteredRadiation;

			calc bandLimitedRadiation.irradiance = incidentFilteredRadiation.irradiance * inBandTransmission;
			calc bandLimitedRadiation.transmittedPower = incidentFilteredRadiation.transmittedPower * inBandTransmission;
			calc bandLimitedRadiation.band = selectedBand;
		}
	}

	part def AbsorberThermopileSensor {
		doc /* Converts absorbed radiant power into a thermoelectric signal. */

		attribute absorptance : DimensionlessRatio = 0.97 [1];
		attribute responsivity : Voltage = 15.0E-6 [V];
		attribute thermalTimeConstant : TimeDuration = 8.0 [s];
		attribute nominalColdJunctionTemperature : Temperature = 25.0 [degC];
		attribute maximumIrradiance : Irradiance = 1500.0 [W/m^2];

		port radiationInput : FilteredRadiationInPort;
		port thermalOutput : ThermalSignalPort;
		port analogOutput : AnalogSignalPort;

		action def ConvertRadiationToThermoelectricSignal {
			in item receivedRadiation : FilteredRadiation;
			out item thermalResponse : ThermalSignal;
			out item voltageResponse : ElectricalSignal;

			attribute absorbedPower : RadiantPower;
			attribute estimatedDeltaTemperature : Temperature;

			calc absorbedPower = receivedRadiation.transmittedPower * absorptance;
			calc estimatedDeltaTemperature = absorbedPower * 100.0 [degC/W];
			calc thermalResponse.coldJunctionTemperature = nominalColdJunctionTemperature;
			calc thermalResponse.hotJunctionTemperature = nominalColdJunctionTemperature + estimatedDeltaTemperature;
			calc thermalResponse.temperatureDifference = estimatedDeltaTemperature;
			calc voltageResponse.voltage = receivedRadiation.irradiance * responsivity;
			calc voltageResponse.current = 0.0 [A];
			calc voltageResponse.sourceImpedance = 100.0 [ohm];
		}
	}

	part def TemperatureSensor {
		doc /* Measures local sensor body temperature for compensation. */

		attribute accuracy : Temperature = 0.2 [degC];
		attribute samplePeriod : TimeDuration = 1.0 [s];

		port analogTemperatureOutput : AnalogSignalPort;

		action def MeasureBodyTemperature {
			out item temperatureSignal : ElectricalSignal;

			attribute sensedTemperature : Temperature = 25.0 [degC];

			calc temperatureSignal.voltage = sensedTemperature * 0.010 [V/degC];
			calc temperatureSignal.current = 0.001 [A];
			calc temperatureSignal.sourceImpedance = 10.0 [ohm];
		}
	}

	part def SignalConditioner {
		doc /* Amplifies and filters weak analog signals before digitization. */

		attribute gain : DimensionlessRatio = 1000.0 [1];
		attribute lowPassCutoffFrequency : Real = 2.0;
		attribute offsetVoltage : Voltage = 0.0 [V];
		attribute inputNoise : Voltage = 1.0E-6 [V];

		port sensorInput : AnalogSignalInPort;
		port temperatureInput : AnalogSignalInPort;
		port conditionedOutput : AnalogSignalPort;

		action def AmplifyAndFilter {
			in item rawSensorSignal : ElectricalSignal;
			in item rawTemperatureSignal : ElectricalSignal;
			out item conditionedSignal : ElectricalSignal;

			calc conditionedSignal.voltage = (rawSensorSignal.voltage + offsetVoltage) * gain;
			calc conditionedSignal.current = rawSensorSignal.current;
			calc conditionedSignal.sourceImpedance = 50.0 [ohm];
		}
	}

	part def AnalogToDigitalConverter {
		doc /* Converts conditioned analog voltage into digital samples. */

		attribute resolutionBits : Integer = 24;
		attribute referenceVoltage : Voltage = 2.500 [V];
		attribute conversionPeriod : TimeDuration = 0.25 [s];
		attribute inputRange : Voltage = 2.500 [V];

		port analogInput : AnalogSignalInPort;
		port digitalOutput : DigitalSamplePort;

		action def DigitizeVoltage {
			in item conditionedSignal : ElectricalSignal;
			out item sample : DigitalSample;

			calc sample.rawCount = conditionedSignal.voltage / referenceVoltage * 16777215 [count];
			calc sample.sampleTime = conversionPeriod;
			calc sample.channelIdentifier = "thermopile";
		}
	}

	part def CalibrationMemory {
		doc /* Stores factory and field calibration data. */

		attribute factoryResponsivity : Voltage = 15.0E-6 [V];
		attribute factoryOffset : Voltage = 0.0 [V];
		attribute factoryTemperatureCoefficient : DimensionlessRatio = 0.001 [1];
		attribute calibratedApertureArea : ApertureArea = 1.000E-4 [m^2];

		port calibrationOutput : CalibrationPort;

		action def ProvideCalibrationData {
			out item calibration : CalibrationData;

			calc calibration.responsivity = factoryResponsivity;
			calc calibration.offsetVoltage = factoryOffset;
			calc calibration.temperatureCoefficient = factoryTemperatureCoefficient;
			calc calibration.apertureArea = calibratedApertureArea;
			calc calibration.validForBand = RadiationBand::broadbandSolar;
		}
	}

	part def MeasurementProcessor {
		doc /* Computes calibrated irradiance from digital samples, calibration coefficients, and compensation values. */

		attribute integrationTime : TimeDuration = 10.0 [s];
		attribute zeroOffsetCount : DigitalCount = 0 [count];
		attribute saturationCount : DigitalCount = 16000000 [count];
		attribute lastComputedIrradiance : Irradiance = 0.0 [W/m^2];
		attribute currentMode : OperatingMode = OperatingMode::idle;
		attribute currentHealth : HealthStatus = HealthStatus::healthy;

		port sampleInput : DigitalSampleInPort;
		port calibrationInput : CalibrationInPort;
		port commandInput : CommandInPort;
		port readingOutput : ReadingOutPort;
		port statusOutput : StatusOutPort;

		action def ComputeIrradiance {
			in item sample : DigitalSample;
			in item calibration : CalibrationData;
			out item reading : IrradianceReading;

			attribute correctedCount : DigitalCount;
			attribute measuredVoltage : Voltage;
			attribute compensatedVoltage : Voltage;

			calc correctedCount = sample.rawCount - zeroOffsetCount;
			calc measuredVoltage = correctedCount / 16777215 [count] * 2.500 [V];
			calc compensatedVoltage = measuredVoltage - calibration.offsetVoltage;
			calc reading.irradiance = compensatedVoltage / calibration.responsivity;
			calc reading.uncertainty = reading.irradiance * 0.02 [1];
			calc reading.integrationTime = integrationTime;
			calc reading.sensorTemperature = 25.0 [degC];
			calc reading.health = currentHealth;
			calc lastComputedIrradiance = reading.irradiance;
		}

		action def GenerateStatus {
			out item status : StatusMessage;

			calc status.mode = currentMode;
			calc status.health = currentHealth;
			calc status.sensorTemperature = 25.0 [degC];
			calc status.lastReading = lastComputedIrradiance;
		}

		state def MeasurementStateMachine {
			entry action GenerateStatus;

			state Off;
			state SelfTest;
			state DarkReference;
			state Ready;
			state Measuring;
			state Saturated;
			state Fault;
			state Maintenance;

			transition initial then Off;

			transition PowerApplied
				first Off
				then SelfTest;

			transition SelfTestPassed
				first SelfTest
				then DarkReference
				effect action {
					currentHealth = HealthStatus::healthy;
					currentMode = OperatingMode::darkReference;
				}

			transition SelfTestFailed
				first SelfTest
				then Fault
				effect action {
					currentHealth = HealthStatus::failed;
					currentMode = OperatingMode::fault;
				}

			transition DarkReferenceComplete
				first DarkReference
				then Ready
				effect action {
					zeroOffsetCount = 0 [count];
					currentMode = OperatingMode::idle;
				}

			transition StartMeasurement
				first Ready
				then Measuring
				effect action {
					currentMode = OperatingMode::measuring;
				}

			transition MeasurementComplete
				first Measuring
				then Ready
				effect action {
					currentMode = OperatingMode::idle;
				}

			transition DetectorSaturated
				first Measuring
				then Saturated
				effect action {
					currentMode = OperatingMode::saturated;
					currentHealth = HealthStatus::degraded;
				}

			transition SaturationCleared
				first Saturated
				then Ready
				effect action {
					currentMode = OperatingMode::idle;
					currentHealth = HealthStatus::healthy;
				}

			transition EnterMaintenance
				first Ready
				then Maintenance
				effect action {
					currentMode = OperatingMode::maintenance;
				}

			transition ExitMaintenance
				first Maintenance
				then Ready
				effect action {
					currentMode = OperatingMode::idle;
				}
		}
	}

	part def UserInterface {
		doc /* Presents irradiance values and accepts commands from the user. */

		attribute displayUpdatePeriod : TimeDuration = 1.0 [s];
		attribute minimumDisplayedIrradiance : Irradiance = 0.0 [W/m^2];
		attribute maximumDisplayedIrradiance : Irradiance = 1500.0 [W/m^2];

		port readingInput : ReadingInPort;
		port commandOutput : CommandInPort;
		port statusInput : StatusOutPort;

		action def DisplayReading {
			in item reading : IrradianceReading;
		}
	}

	part def DataInterface {
		doc /* Provides machine-readable actinometer readings to an external logger or control system. */

		attribute nominalDataRate : DataRate = 115200 [bit/s];
		attribute publicationPeriod : TimeDuration = 1.0 [s];

		port readingInput : ReadingInPort;
		port statusInput : StatusOutPort;
		port commandInput : CommandInPort;
	}

	part def PowerSupply {
		doc /* Converts incoming electrical power into regulated internal rails. */

		attribute inputVoltageMinimum : Voltage = 9.0 [V];
		attribute inputVoltageMaximum : Voltage = 36.0 [V];
		attribute regulatedVoltage : Voltage = 5.0 [V];
		attribute maximumOutputPower : Power = 5.0 [W];

		port externalPower : PowerInPort;
		port internalPower : PowerOutPort;

		action def RegulatePower {
			in item inputPower : ElectricalPower;
			out item outputPower : ElectricalPower;

			calc outputPower.voltage = regulatedVoltage;
			calc outputPower.current = maximumOutputPower / regulatedVoltage;
			calc outputPower.availablePower = maximumOutputPower;
		}
	}

	part def Actinometer {
		doc /* 
			System that measures incident solar irradiance. At a high level, the actinometer collects incident radiation, converts it to a proportional sensor signal, digitizes the signal, applies calibration and compensation, and outputs a calibrated irradiance reading.
		*/

		attribute measurementRangeMinimum : Irradiance = 0.0 [W/m^2];
		attribute measurementRangeMaximum : Irradiance = 1500.0 [W/m^2];
		attribute absoluteAccuracy : DimensionlessRatio = 0.02 [1];
		attribute responseTime : TimeDuration = 10.0 [s];
		attribute effectiveApertureArea : ApertureArea = 1.000E-4 [m^2];
		attribute supportedBand : RadiationBand = RadiationBand::broadbandSolar;

		port solarInput : RadiationInPort;
		port powerInput : PowerInPort;
		port commandInput : CommandInPort;
		port irradianceOutput : ReadingOutPort;
		port statusOutput : StatusOutPort;

		part aperture : OpticalAperture {
			:>> effectiveArea = effectiveApertureArea;
		}

		part filter : SpectralFilter {
			:>> selectedBand = supportedBand;
		}

		part detector : AbsorberThermopileSensor {
			:>> maximumIrradiance = measurementRangeMaximum;
		}

		part temperatureSensor : TemperatureSensor;

		part conditioner : SignalConditioner;

		part adc : AnalogToDigitalConverter;

		part calibrationMemory : CalibrationMemory {
			:>> calibratedApertureArea = effectiveApertureArea;
		}

		part processor : MeasurementProcessor {
			:>> integrationTime = responseTime;
		}

		part userInterface : UserInterface;

		part dataInterface : DataInterface;

		part powerSupply : PowerSupply;

		connect solarInput to aperture.incident;
		connect aperture.filtered to filter.input;
		connect filter.output to detector.radiationInput;
		connect detector.analogOutput to conditioner.sensorInput;
		connect temperatureSensor.analogTemperatureOutput to conditioner.temperatureInput;
		connect conditioner.conditionedOutput to adc.analogInput;
		connect adc.digitalOutput to processor.sampleInput;
		connect calibrationMemory.calibrationOutput to processor.calibrationInput;
		connect processor.readingOutput to irradianceOutput;
		connect processor.statusOutput to statusOutput;
		connect processor.readingOutput to userInterface.readingInput;
		connect processor.readingOutput to dataInterface.readingInput;
		connect processor.statusOutput to userInterface.statusInput;
		connect processor.statusOutput to dataInterface.statusInput;
		connect commandInput to processor.commandInput;
		connect powerInput to powerSupply.externalPower;

		action def PerformPrimaryFunction {
			doc /* Receive solar radiation and produce a calibrated solar irradiance reading. */

			in item incidentRadiation : SolarRadiation;
			in item calibration : CalibrationData;
			out item reading : IrradianceReading;

			action collect : OpticalAperture::LimitAndTransmitRadiation;
			action bandLimit : SpectralFilter::ApplySpectralResponse;
			action transduce : AbsorberThermopileSensor::ConvertRadiationToThermoelectricSignal;
			action condition : SignalConditioner::AmplifyAndFilter;
			action digitize : AnalogToDigitalConverter::DigitizeVoltage;
			action compute : MeasurementProcessor::ComputeIrradiance;

			flow incidentRadiation to collect.inputRadiation;
			flow collect.outputRadiation to bandLimit.incidentFilteredRadiation;
			flow bandLimit.bandLimitedRadiation to transduce.receivedRadiation;
			flow transduce.voltageResponse to condition.rawSensorSignal;
			flow digitize.sample to compute.sample;
			flow calibration to compute.calibration;
			flow compute.reading to reading;
		}
	}

	requirement def PrimaryFunctionRequirement {
		doc /* The actinometer shall measure incident solar radiation and provide a calibrated irradiance reading. */

		subject actinometer : Actinometer;

		require constraint {
			actinometer.irradianceOutput.reading.irradiance >= actinometer.measurementRangeMinimum and
			actinometer.irradianceOutput.reading.irradiance <= actinometer.measurementRangeMaximum
		}
	}

	requirement def RadiationCollectionRequirement {
		doc /* The actinometer shall admit solar radiation through a calibrated aperture with a defined effective receiving area and field of view. */

		subject aperture : OpticalAperture;

		require constraint {
			aperture.effectiveArea == 1.000E-4 [m^2] and
			aperture.fieldOfView <= 5.0 [deg]
		}
	}

	requirement def ConversionRequirement {
		doc /* The detector shall convert received filtered radiation into an electrical signal proportional to irradiance. */

		subject detector : AbsorberThermopileSensor;

		require constraint {
			detector.responsivity > 0.0 [V] and
			detector.absorptance >= 0.95 [1]
		}
	}

	requirement def CalibrationRequirement {
		doc /* The processor shall use stored calibration data to compensate raw measurement samples before reporting irradiance. */

		subject processor : MeasurementProcessor;

		require constraint {
			processor.integrationTime >= 1.0 [s] and
			processor.integrationTime <= 60.0 [s]
		}
	}

	requirement def AccuracyRequirement {
		doc /* For irradiance within the specified range, the reported value shall have an uncertainty not exceeding two percent of reading. */

		subject actinometer : Actinometer;

		require constraint {
			actinometer.absoluteAccuracy <= 0.02 [1]
		}
	}

	requirement def ResponseTimeRequirement {
		doc /* The actinometer shall provide an updated calibrated irradiance reading within ten seconds after a valid measurement command. */

		subject actinometer : Actinometer;

		require constraint {
			actinometer.responseTime <= 10.0 [s]
		}
	}

	requirement def SaturationDetectionRequirement {
		doc /* The measurement processor shall indicate saturated operating mode when the digitized sensor signal exceeds the saturation threshold. */

		subject processor : MeasurementProcessor;

		require constraint {
			processor.saturationCount < 16777215 [count]
		}
	}

	requirement def StatusReportingRequirement {
		doc /* The actinometer shall report operating mode, health status, sensor temperature, and last irradiance reading. */

		subject actinometer : Actinometer;

		require constraint {
			actinometer.statusOutput.status.health != HealthStatus::failed or
			actinometer.statusOutput.status.mode == OperatingMode::fault
		}
	}

	requirement def PowerRequirement {
		doc /* The actinometer shall operate from a nominal external low-voltage DC supply and regulate internal power for all measurement electronics. */

		subject supply : PowerSupply;

		require constraint {
			supply.inputVoltageMinimum <= 12.0 [V] and
			supply.inputVoltageMaximum >= 24.0 [V] and
			supply.maximumOutputPower >= 2.0 [W]
		}
	}

	part actinometerSystem : Actinometer {
		:>> measurementRangeMinimum = 0.0 [W/m^2];
		:>> measurementRangeMaximum = 1500.0 [W/m^2];
		:>> absoluteAccuracy = 0.02 [1];
		:>> responseTime = 10.0 [s];
		:>> effectiveApertureArea = 1.000E-4 [m^2];
		:>> supportedBand = RadiationBand::broadbandSolar;
	}

	satisfy PrimaryFunctionRequirement by actinometerSystem;
	satisfy RadiationCollectionRequirement by actinometerSystem.aperture;
	satisfy ConversionRequirement by actinometerSystem.detector;
	satisfy CalibrationRequirement by actinometerSystem.processor;
	satisfy AccuracyRequirement by actinometerSystem;
	satisfy ResponseTimeRequirement by actinometerSystem;
	satisfy SaturationDetectionRequirement by actinometerSystem.processor;
	satisfy StatusReportingRequirement by actinometerSystem;
	satisfy PowerRequirement by actinometerSystem.powerSupply;
}

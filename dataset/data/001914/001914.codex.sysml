package EngineeringSystemModel {

    private import ScalarValues::*;
    private import SI::*;

    attribute def Percent :> Real {
        unit = "%";
    }

    attribute def Celsius :> Real {
        unit = "degC";
    }

    attribute def Kilowatt :> Real {
        unit = "kW";
    }

    attribute def Megabyte :> Real {
        unit = "MB";
    }

    attribute def Seconds :> Real {
        unit = "s";
    }

    item def EngineeringRequest {
        attribute requestId : String;
        attribute requestedDiscipline : EngineeringDiscipline;
        attribute priority : RequestPriority;
        attribute requiredCompletionTime : Seconds;
        attribute description : String;
    }

    item def EngineeringResult {
        attribute resultId : String;
        attribute status : ResultStatus;
        attribute confidence : Percent;
        attribute summary : String;
    }

    item def DesignModel {
        attribute modelId : String;
        attribute version : String;
        attribute maturity : Percent;
        attribute size : Megabyte;
    }

    item def AnalysisData {
        attribute datasetId : String;
        attribute thermalMargin : Celsius;
        attribute structuralMargin : Percent;
        attribute powerDemand : Kilowatt;
    }

    item def VerificationRecord {
        attribute recordId : String;
        attribute verified : Boolean;
        attribute requirementCoverage : Percent;
    }

    enum def EngineeringDiscipline {
        mechanical;
        electrical;
        software;
        systems;
        manufacturing;
    }

    enum def RequestPriority {
        routine;
        elevated;
        urgent;
    }

    enum def ResultStatus {
        accepted;
        rejected;
        reworkRequired;
        verified;
    }

    port def RequestPort {
        in item request : EngineeringRequest;
    }

    port def ResultPort {
        out item result : EngineeringResult;
    }

    port def ModelExchangePort {
        inout item designModel : DesignModel;
    }

    port def AnalysisPort {
        out item analysisData : AnalysisData;
    }

    port def VerificationPort {
        in item verificationRecord : VerificationRecord;
        out item verificationRecord : VerificationRecord;
    }

    port def PowerPort {
        in attribute suppliedPower : Kilowatt;
    }

    part def EngineeringManagementSystem {
        attribute operationalAvailability : Percent;
        attribute maxConcurrentRequests : Integer;
        attribute nominalProcessingTime : Seconds;
        attribute peakPowerDemand : Kilowatt;

        port requestIn : RequestPort;
        port resultOut : ResultPort;
        port externalModelExchange : ModelExchangePort;
        port powerIn : PowerPort;

        part intake : RequestIntake;
        part designRepository : DesignRepository;
        part analysisEngine : AnalysisEngine;
        part verificationController : VerificationController;
        part reportingService : ReportingService;
        part operatorConsole : OperatorConsole;

        connection requestFlow connect requestIn to intake.requestInput;
        connection acceptedRequestFlow connect intake.acceptedRequestOutput to analysisEngine.requestInput;
        connection modelAccessFlow connect designRepository.modelPort to analysisEngine.modelPort;
        connection externalModelFlow connect externalModelExchange to designRepository.externalModelPort;
        connection analysisToVerification connect analysisEngine.analysisOutput to verificationController.analysisInput;
        connection verificationToReporting connect verificationController.verificationOutput to reportingService.verificationInput;
        connection reportResultFlow connect reportingService.resultOutput to resultOut;
        connection consoleRequestFlow connect operatorConsole.requestPort to intake.consoleRequestPort;
        connection consoleResultFlow connect reportingService.consoleResultPort to operatorConsole.resultPort;
        connection powerDistribution connect powerIn to analysisEngine.powerPort;

        perform action manageEngineeringLifecycle;
        exhibit state engineeringSystemStates;
    }

    part def RequestIntake {
        attribute queueDepth : Integer;
        attribute rejectionThreshold : Integer;

        port requestInput : RequestPort;
        port consoleRequestPort : RequestPort;
        port acceptedRequestOutput : RequestPort;

        action validateRequest {
            in item rawRequest : EngineeringRequest;
            out item acceptedRequest : EngineeringRequest;
            out attribute valid : Boolean;
        }
    }

    part def DesignRepository {
        attribute storedModelCount : Integer;
        attribute maximumStorage : Megabyte;
        attribute currentStorageUse : Megabyte;

        port modelPort : ModelExchangePort;
        port externalModelPort : ModelExchangePort;

        action retrieveLatestModel {
            in attribute discipline : EngineeringDiscipline;
            out item model : DesignModel;
        }

        action storeUpdatedModel {
            in item model : DesignModel;
            out attribute stored : Boolean;
        }
    }

    part def AnalysisEngine {
        attribute processingLoad : Percent;
        attribute nominalPower : Kilowatt;
        attribute maximumPower : Kilowatt;
        attribute maximumThermalMargin : Celsius;

        port requestInput : RequestPort;
        port modelPort : ModelExchangePort;
        port analysisOutput : AnalysisPort;
        port powerPort : PowerPort;

        action performEngineeringAnalysis {
            in item request : EngineeringRequest;
            in item model : DesignModel;
            out item analysis : AnalysisData;
        }

        action generateDesignAlternative {
            in item request : EngineeringRequest;
            in item baselineModel : DesignModel;
            out item updatedModel : DesignModel;
        }
    }

    part def VerificationController {
        attribute minimumCoverage : Percent;
        attribute minimumConfidence : Percent;

        port analysisInput : AnalysisPort;
        port verificationOutput : VerificationPort;

        action verifyAnalysis {
            in item analysis : AnalysisData;
            out item record : VerificationRecord;
        }

        action determineDisposition {
            in item record : VerificationRecord;
            out attribute status : ResultStatus;
        }
    }

    part def ReportingService {
        attribute reportGenerationTime : Seconds;

        port verificationInput : VerificationPort;
        port resultOutput : ResultPort;
        port consoleResultPort : ResultPort;

        action publishResult {
            in item record : VerificationRecord;
            out item result : EngineeringResult;
        }
    }

    part def OperatorConsole {
        attribute activeUsers : Integer;
        attribute displayRefreshTime : Seconds;

        port requestPort : RequestPort;
        port resultPort : ResultPort;
    }

    action def ManageEngineeringLifecycle {
        in item request : EngineeringRequest;
        out item result : EngineeringResult;

        first start;
        then validateRequest;
        then retrieveModel;
        then analyzeDesign;
        then verifyOutcome;
        then publishEngineeringResult;
        then done;

        action start;
        action validateRequest;
        action retrieveModel;
        action analyzeDesign;
        action verifyOutcome;
        action publishEngineeringResult;
        action done;
    }

    state def EngineeringSystemStates {
        entry action initializeSystem;

        state Offline;
        state Ready;
        state AcceptingRequest;
        state Analyzing;
        state Verifying;
        state Reporting;
        state Faulted;

        transition initial then Offline;
        transition powerApplied first Offline then Ready;
        transition requestReceived first Ready then AcceptingRequest;
        transition requestAccepted first AcceptingRequest then Analyzing;
        transition analysisComplete first Analyzing then Verifying;
        transition verificationComplete first Verifying then Reporting;
        transition reportPublished first Reporting then Ready;
        transition invalidRequest first AcceptingRequest then Ready;
        transition processingFault first Ready then Faulted;
        transition analysisFault first Analyzing then Faulted;
        transition verificationFault first Verifying then Faulted;
        transition faultCleared first Faulted then Ready;
    }

    requirement def PrimaryFunctionRequirement {
        doc /* The Engineering Management System shall transform validated engineering requests into verified engineering results by coordinating design model retrieval, engineering analysis, verification, and reporting. */

        subject system : EngineeringManagementSystem;

        require constraint {
            system.operationalAvailability >= 99.0 [%]
        }
    }

    requirement def ThroughputRequirement {
        doc /* The system shall support concurrent processing of at least 25 active engineering requests. */

        subject system : EngineeringManagementSystem;

        require constraint {
            system.maxConcurrentRequests >= 25
        }
    }

    requirement def TimelinessRequirement {
        doc /* Routine engineering requests shall produce a published result within 900 seconds under nominal load. */

        subject system : EngineeringManagementSystem;

        require constraint {
            system.nominalProcessingTime <= 900 [s]
        }
    }

    requirement def VerificationCoverageRequirement {
        doc /* Verification records shall demonstrate at least 95 percent requirement coverage before an engineering result is marked verified. */

        subject verifier : VerificationController;

        require constraint {
            verifier.minimumCoverage >= 95.0 [%]
        }
    }

    requirement def PowerRequirement {
        doc /* The engineering analysis subsystem shall not exceed 12 kilowatts during peak computation. */

        subject engine : AnalysisEngine;

        require constraint {
            engine.maximumPower <= 12 [kW]
        }
    }

    requirement def StorageRequirement {
        doc /* The design repository shall provide at least 500000 megabytes of model storage capacity. */

        subject repository : DesignRepository;

        require constraint {
            repository.maximumStorage >= 500000 [MB]
        }
    }

    part engineeringSystem : EngineeringManagementSystem {
        attribute operationalAvailability = 99.5 [%];
        attribute maxConcurrentRequests = 40;
        attribute nominalProcessingTime = 600 [s];
        attribute peakPowerDemand = 11.5 [kW];

        part intake {
            attribute queueDepth = 0;
            attribute rejectionThreshold = 100;
        }

        part designRepository {
            attribute storedModelCount = 12500;
            attribute maximumStorage = 750000 [MB];
            attribute currentStorageUse = 420000 [MB];
        }

        part analysisEngine {
            attribute processingLoad = 35.0 [%];
            attribute nominalPower = 6.5 [kW];
            attribute maximumPower = 11.5 [kW];
            attribute maximumThermalMargin = 45.0 [degC];
        }

        part verificationController {
            attribute minimumCoverage = 95.0 [%];
            attribute minimumConfidence = 90.0 [%];
        }

        part reportingService {
            attribute reportGenerationTime = 30 [s];
        }

        part operatorConsole {
            attribute activeUsers = 4;
            attribute displayRefreshTime = 2 [s];
        }
    }

    satisfy PrimaryFunctionRequirement by engineeringSystem;
    satisfy ThroughputRequirement by engineeringSystem;
    satisfy TimelinessRequirement by engineeringSystem;
    satisfy VerificationCoverageRequirement by engineeringSystem.verificationController;
    satisfy PowerRequirement by engineeringSystem.analysisEngine;
    satisfy StorageRequirement by engineeringSystem.designRepository;
}

package GyroscopeSystemModel {

    import ScalarValues::*;
    import ISQ::*;
    import SI::*;

    attribute def AngularRate : Real {
        unit = "rad/s";
    }

    attribute def AngularAcceleration : Real {
        unit = "rad/s^2";
    }

    attribute def Angle : Real {
        unit = "rad";
    }

    attribute def Torque : Real {
        unit = "N*m";
    }

    attribute def RotationalSpeed : Real {
        unit = "rev/min";
    }

    attribute def Voltage : Real {
        unit = "V";
    }

    attribute def Current : Real {
        unit = "A";
    }

    attribute def Temperature : Real {
        unit = "degC";
    }

    attribute def TimeInterval : Real {
        unit = "s";
    }

    attribute def DimensionlessRatio : Real;

    item def ElectricalPower {
        attribute voltage : Voltage;
        attribute current : Current;
    }

    item def AngularMotion {
        attribute rollRate : AngularRate;
        attribute pitchRate : AngularRate;
        attribute yawRate : AngularRate;
        attribute rollAngle : Angle;
        attribute pitchAngle : Angle;
        attribute yawAngle : Angle;
    }

    item def SpinState {
        attribute rotorSpeed : RotationalSpeed;
        attribute angularMomentum : Real {
            unit = "kg*m^2/s";
        }
        attribute bearingTemperature : Temperature;
    }

    item def OrientationEstimate {
        attribute roll : Angle;
        attribute pitch : Angle;
        attribute yaw : Angle;
        attribute confidence : DimensionlessRatio;
        attribute sampleAge : TimeInterval;
    }

    item def HealthStatus {
        attribute ready : Boolean;
        attribute faulted : Boolean;
        attribute messageCode : Integer;
        attribute temperatureMargin : Temperature;
    }

    port def PowerInputPort {
        in item power : ElectricalPower;
    }

    port def MotionInputPort {
        in item motion : AngularMotion;
    }

    port def OrientationOutputPort {
        out item orientation : OrientationEstimate;
    }

    port def HealthOutputPort {
        out item health : HealthStatus;
    }

    port def ControlPort {
        in item enableCommand : Boolean;
        in item resetCommand : Boolean;
    }

    part def GyroscopeSystem {
        doc
        /*
         * High-level primary function:
         * The gyroscope system senses angular motion about three orthogonal axes and
         * produces a stable orientation estimate for a host vehicle, instrument,
         * or navigation controller.
         */

        port powerIn : PowerInputPort;
        port bodyMotionIn : MotionInputPort;
        port orientationOut : OrientationOutputPort;
        port healthOut : HealthOutputPort;
        port controlIn : ControlPort;

        attribute operatingVoltage : Voltage = 5.0;
        attribute maximumCurrent : Current = 0.35;
        attribute nominalRotorSpeed : RotationalSpeed = 24000.0;
        attribute startupTimeLimit : TimeInterval = 3.0;
        attribute angularRateRange : AngularRate = 8.73;
        attribute biasStability : AngularRate = 0.00035;
        attribute maximumOperatingTemperature : Temperature = 85.0;
        attribute minimumOperatingTemperature : Temperature = -40.0;

        part powerConditioner : PowerConditioner;
        part rotorAssembly : RotorAssembly;
        part frameAssembly : GimbalFrameAssembly;
        part angularSensor : AngularMotionSensor;
        part signalProcessor : GyroSignalProcessor;
        part healthMonitor : HealthMonitor;

        connect powerIn to powerConditioner.rawPowerIn;
        connect powerConditioner.conditionedPowerOut to rotorAssembly.powerIn;
        connect powerConditioner.conditionedPowerOut to angularSensor.powerIn;
        connect powerConditioner.conditionedPowerOut to signalProcessor.powerIn;
        connect powerConditioner.conditionedPowerOut to healthMonitor.powerIn;

        connect bodyMotionIn to frameAssembly.motionIn;
        connect frameAssembly.relativeMotionOut to angularSensor.motionIn;
        connect rotorAssembly.spinStateOut to angularSensor.spinStateIn;
        connect angularSensor.rawMeasurementOut to signalProcessor.measurementIn;
        connect signalProcessor.orientationOut to orientationOut;
        connect rotorAssembly.spinStateOut to healthMonitor.spinStateIn;
        connect signalProcessor.processingHealthOut to healthMonitor.processorHealthIn;
        connect healthMonitor.healthOut to healthOut;
        connect controlIn to signalProcessor.controlIn;
        connect controlIn to rotorAssembly.controlIn;

        perform action initializeSystem : InitializeGyroscope;
        perform action estimateOrientation : EstimateOrientation;
        perform state gyroOperationalStates : GyroscopeOperatingStateMachine;
    }

    part def PowerConditioner {
        port rawPowerIn : PowerInputPort;
        port conditionedPowerOut : PowerInputPort;

        attribute inputVoltage : Voltage;
        attribute regulatedVoltage : Voltage = 5.0;
        attribute rippleLimit : Voltage = 0.02;
        attribute efficiency : DimensionlessRatio = 0.90;
    }

    part def RotorAssembly {
        port powerIn : PowerInputPort;
        port controlIn : ControlPort;
        port spinStateOut {
            out item spin : SpinState;
        }

        attribute rotorSpeed : RotationalSpeed;
        attribute targetRotorSpeed : RotationalSpeed = 24000.0;
        attribute spinUpDuration : TimeInterval = 2.0;
        attribute rotorInertia : Real {
            unit = "kg*m^2";
        } = 0.000018;
        attribute driveTorque : Torque = 0.004;

        part rotor : SpinningRotor;
        part motor : SpinMotor;
        part bearingSet : LowFrictionBearingSet;

        connect powerIn to motor.powerIn;
        connect motor.shaftTorqueOut to rotor.driveTorqueIn;

        perform state rotorStates : RotorStateMachine;
    }

    part def SpinningRotor {
        port driveTorqueIn {
            in item appliedTorque : Torque;
        }

        attribute speed : RotationalSpeed;
        attribute polarMomentOfInertia : Real {
            unit = "kg*m^2";
        } = 0.000018;
        attribute angularMomentum : Real {
            unit = "kg*m^2/s";
        }
    }

    part def SpinMotor {
        port powerIn : PowerInputPort;
        port shaftTorqueOut {
            out item torque : Torque;
        }

        attribute motorCurrent : Current;
        attribute commandedTorque : Torque;
        attribute maximumTorque : Torque = 0.006;
    }

    part def LowFrictionBearingSet {
        attribute frictionTorque : Torque = 0.00004;
        attribute temperature : Temperature;
        attribute maximumTemperature : Temperature = 95.0;
    }

    part def GimbalFrameAssembly {
        port motionIn : MotionInputPort;
        port relativeMotionOut : MotionInputPort;

        attribute rollDeflection : Angle;
        attribute pitchDeflection : Angle;
        attribute yawDeflection : Angle;
        attribute mechanicalDamping : DimensionlessRatio = 0.18;

        part outerFrame : SupportFrame;
        part innerFrame : SupportFrame;
        part flexureMount : FlexureMount;
    }

    part def SupportFrame {
        attribute stiffness : Real {
            unit = "N*m/rad";
        } = 0.42;
        attribute maximumDeflection : Angle = 0.35;
    }

    part def FlexureMount {
        attribute crossAxisSensitivity : DimensionlessRatio = 0.005;
        attribute dampingRatio : DimensionlessRatio = 0.18;
    }

    part def AngularMotionSensor {
        port powerIn : PowerInputPort;
        port motionIn : MotionInputPort;
        port spinStateIn {
            in item spin : SpinState;
        }
        port rawMeasurementOut {
            out item measuredMotion : AngularMotion;
        }

        attribute measurementRange : AngularRate = 8.73;
        attribute noiseDensity : Real {
            unit = "rad/s/sqrt(Hz)";
        } = 0.00008;
        attribute scaleFactorError : DimensionlessRatio = 0.002;
        attribute biasRate : AngularRate = 0.00035;

        part pickoffElectronics : PickoffElectronics;
        part temperatureSensor : TemperatureSensor;
    }

    part def PickoffElectronics {
        attribute samplePeriod : TimeInterval = 0.001;
        attribute analogBandwidth : Real {
            unit = "Hz";
        } = 250.0;
        attribute quantizationResolution : Integer = 16;
    }

    part def TemperatureSensor {
        attribute measuredTemperature : Temperature;
        attribute accuracy : Temperature = 1.0;
    }

    part def GyroSignalProcessor {
        port powerIn : PowerInputPort;
        port measurementIn {
            in item measuredMotion : AngularMotion;
        }
        port orientationOut : OrientationOutputPort;
        port processingHealthOut {
            out item processingHealth : HealthStatus;
        }
        port controlIn : ControlPort;

        attribute integrationStep : TimeInterval = 0.001;
        attribute filterTimeConstant : TimeInterval = 0.05;
        attribute estimatedRoll : Angle;
        attribute estimatedPitch : Angle;
        attribute estimatedYaw : Angle;
        attribute confidence : DimensionlessRatio;

        action calibrateBias {
            in item stationaryMotion : AngularMotion;
            out attribute rollBias : AngularRate;
            out attribute pitchBias : AngularRate;
            out attribute yawBias : AngularRate;
        }

        action integrateAngularRate {
            in item correctedMotion : AngularMotion;
            in attribute step : TimeInterval;
            out item estimate : OrientationEstimate;
        }

        action filterNoise {
            in item unfilteredMotion : AngularMotion;
            out item filteredMotion : AngularMotion;
        }
    }

    part def HealthMonitor {
        port powerIn : PowerInputPort;
        port spinStateIn {
            in item spin : SpinState;
        }
        port processorHealthIn {
            in item processingHealth : HealthStatus;
        }
        port healthOut : HealthOutputPort;

        attribute undervoltageLimit : Voltage = 4.75;
        attribute overtemperatureLimit : Temperature = 85.0;
        attribute minimumReadySpeed : RotationalSpeed = 23500.0;
        attribute maximumReadySpeed : RotationalSpeed = 24500.0;

        action evaluateHealth {
            in item spin : SpinState;
            out item health : HealthStatus;
        }
    }

    action def InitializeGyroscope {
        in item suppliedPower : ElectricalPower;
        out item initializedHealth : HealthStatus;

        first startPowerRegulation;
        then spinRotor;
        then calibrateSensorBias;
        then reportReady;

        action startPowerRegulation;
        action spinRotor;
        action calibrateSensorBias;
        action reportReady;
    }

    action def EstimateOrientation {
        in item bodyAngularMotion : AngularMotion;
        out item orientation : OrientationEstimate;

        first acquireMotionSample;
        then compensateBiasAndScale;
        then integrateRates;
        then publishOrientation;

        action acquireMotionSample;
        action compensateBiasAndScale;
        action integrateRates;
        action publishOrientation;
    }

    state def RotorStateMachine {
        entry action clearRotorFault;

        state stopped;
        state spinningUp;
        state synchronized;
        state overspeedFault;
        state underspeedFault;

        initial then stopped;

        transition stopped_to_spinningUp
            first stopped
            accept enableCommand
            then spinningUp;

        transition spinningUp_to_synchronized
            first spinningUp
            if rotorSpeed >= 23500.0 and rotorSpeed <= 24500.0
            then synchronized;

        transition synchronized_to_overspeedFault
            first synchronized
            if rotorSpeed > 25200.0
            then overspeedFault;

        transition synchronized_to_underspeedFault
            first synchronized
            if rotorSpeed < 22800.0
            then underspeedFault;

        transition fault_to_stopped
            first overspeedFault
            accept resetCommand
            then stopped;

        transition underspeedFault_to_stopped
            first underspeedFault
            accept resetCommand
            then stopped;

        action clearRotorFault;
    }

    state def GyroscopeOperatingStateMachine {
        state unpowered;
        state initializing;
        state calibrating;
        state ready;
        state measuring;
        state degraded;
        state failed;

        initial then unpowered;

        transition unpowered_to_initializing
            first unpowered
            if powerIn.power.voltage >= 4.75
            then initializing;

        transition initializing_to_calibrating
            first initializing
            if rotorAssembly.rotorSpeed >= 23500.0
            then calibrating;

        transition calibrating_to_ready
            first calibrating
            if signalProcessor.confidence >= 0.95
            then ready;

        transition ready_to_measuring
            first ready
            accept enableCommand
            then measuring;

        transition measuring_to_degraded
            first measuring
            if healthMonitor.minimumReadySpeed > rotorAssembly.rotorSpeed
            then degraded;

        transition degraded_to_measuring
            first degraded
            if rotorAssembly.rotorSpeed >= 23500.0 and signalProcessor.confidence >= 0.90
            then measuring;

        transition any_to_failed_by_temperature
            first measuring
            if rotorAssembly.bearingSet.temperature > 95.0
            then failed;

        transition failed_to_initializing
            first failed
            accept resetCommand
            then initializing;
    }

    requirement def PrimaryFunctionRequirement {
        doc
        /*
         * The system shall convert sensed angular motion into a stable orientation
         * estimate about roll, pitch, and yaw axes for use by a host controller.
         */

        subject gyro : GyroscopeSystem;

        require constraint {
            gyro.orientationOut.orientation.confidence >= 0.95
        }
    }

    requirement def StartupRequirement {
        subject gyro : GyroscopeSystem;

        require constraint {
            gyro.startupTimeLimit <= 3.0
        }
    }

    requirement def RotorSpeedRequirement {
        subject rotorAssembly : RotorAssembly;

        require constraint {
            rotorAssembly.rotorSpeed >= 23500.0 and rotorAssembly.rotorSpeed <= 24500.0
        }
    }

    requirement def ElectricalPowerRequirement {
        subject gyro : GyroscopeSystem;

        require constraint {
            gyro.powerIn.power.voltage >= 4.75 and gyro.powerIn.power.voltage <= 5.25 and
            gyro.powerIn.power.current <= gyro.maximumCurrent
        }
    }

    requirement def OperatingTemperatureRequirement {
        subject gyro : GyroscopeSystem;

        require constraint {
            gyro.minimumOperatingTemperature <= gyro.rotorAssembly.bearingSet.temperature and
            gyro.rotorAssembly.bearingSet.temperature <= gyro.maximumOperatingTemperature
        }
    }

    requirement def AngularRateMeasurementRequirement {
        subject sensor : AngularMotionSensor;

        require constraint {
            sensor.measurementRange >= 8.73 and
            sensor.scaleFactorError <= 0.002
        }
    }

    requirement def HealthReportingRequirement {
        subject gyro : GyroscopeSystem;

        require constraint {
            gyro.healthOut.health.ready == true implies
            gyro.rotorAssembly.rotorSpeed >= 23500.0 and
            gyro.rotorAssembly.rotorSpeed <= 24500.0
        }
    }

    part gyroscopeNavigationUnit : GyroscopeSystem {
        attribute operatingVoltage = 5.0;
        attribute maximumCurrent = 0.35;
        attribute nominalRotorSpeed = 24000.0;
        attribute angularRateRange = 8.73;
    }

    satisfy PrimaryFunctionRequirement by gyroscopeNavigationUnit;
    satisfy StartupRequirement by gyroscopeNavigationUnit;
    satisfy ElectricalPowerRequirement by gyroscopeNavigationUnit;
    satisfy OperatingTemperatureRequirement by gyroscopeNavigationUnit;
    satisfy HealthReportingRequirement by gyroscopeNavigationUnit;
}

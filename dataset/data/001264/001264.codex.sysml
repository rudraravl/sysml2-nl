package StrainGaugeMeasurementSystem {

    import ScalarValues::*;
    import SI::*;

    attribute def Microstrain :> Real {
        unit = "µε";
    }

    attribute def ResistanceOhm :> Real {
        unit = "Ohm";
    }

    attribute def VoltageVolt :> Real {
        unit = "V";
    }

    attribute def CurrentAmpere :> Real {
        unit = "A";
    }

    attribute def TemperatureCelsius :> Real {
        unit = "degC";
    }

    attribute def FrequencyHertz :> Real {
        unit = "Hz";
    }

    attribute def ForceNewton :> Real {
        unit = "N";
    }

    attribute def CalibrationFactor :> Real;

    item def MechanicalStrain {
        attribute strain : Microstrain;
        attribute principalAxisAngle : Real {
            unit = "deg";
        }
    }

    item def AnalogVoltageSignal {
        attribute voltage : VoltageVolt;
        attribute noiseRms : VoltageVolt;
        attribute bandwidth : FrequencyHertz;
    }

    item def DigitizedMeasurement {
        attribute sampleIndex : Integer;
        attribute timestamp : Real {
            unit = "s";
        }
        attribute rawAdcCount : Integer;
        attribute bridgeVoltage : VoltageVolt;
    }

    item def CompensatedStrainMeasurement {
        attribute strain : Microstrain;
        attribute temperature : TemperatureCelsius;
        attribute uncertainty : Microstrain;
        attribute valid : Boolean;
    }

    item def DiagnosticStatus {
        attribute bridgeOpenCircuit : Boolean;
        attribute bridgeShortCircuit : Boolean;
        attribute excitationOutOfRange : Boolean;
        attribute saturationDetected : Boolean;
        attribute calibrationExpired : Boolean;
        attribute measurementHealthy : Boolean;
    }

    port def MechanicalBondPort {
        in item appliedStrain : MechanicalStrain;
    }

    port def AnalogSignalPort {
        out item signal : AnalogVoltageSignal;
    }

    port def AnalogInputPort {
        in item signal : AnalogVoltageSignal;
    }

    port def DigitalMeasurementPort {
        out item measurement : DigitizedMeasurement;
    }

    port def StrainOutputPort {
        out item strainMeasurement : CompensatedStrainMeasurement;
    }

    port def DiagnosticPort {
        out item status : DiagnosticStatus;
    }

    port def PowerPort {
        in item supplyVoltage : AnalogVoltageSignal;
    }

    port def ExcitationPort {
        out item excitationVoltage : AnalogVoltageSignal;
    }

    part def StrainGaugeElement {
        attribute nominalResistance : ResistanceOhm = 350.0;
        attribute gaugeFactor : CalibrationFactor = 2.10;
        attribute maxStrain : Microstrain = 10000.0;
        attribute resistanceChange : ResistanceOhm;
        attribute selfHeatingTemperatureRise : TemperatureCelsius;

        port substrateInterface : MechanicalBondPort;
        port resistanceOutput : AnalogSignalPort;

        action def ConvertStrainToResistance {
            in item inputStrain : MechanicalStrain;
            out item resistanceSignal : AnalogVoltageSignal;
            attribute deltaResistance : ResistanceOhm;
        }
    }

    part def WheatstoneBridge {
        attribute bridgeResistance : ResistanceOhm = 350.0;
        attribute completionResistorTolerance : Real = 0.001;
        attribute bridgeBalanceOffset : VoltageVolt;
        attribute excitationVoltage : VoltageVolt = 5.0;

        port excitationIn : AnalogInputPort;
        port gaugeLegIn : AnalogInputPort;
        port bridgeOut : AnalogSignalPort;

        action def GenerateDifferentialVoltage {
            in item gaugeResistanceSignal : AnalogVoltageSignal;
            in item excitation : AnalogVoltageSignal;
            out item bridgeSignal : AnalogVoltageSignal;
        }
    }

    part def ExcitationSupply {
        attribute nominalOutputVoltage : VoltageVolt = 5.0;
        attribute outputCurrentLimit : CurrentAmpere = 0.025;
        attribute voltageTolerance : Real = 0.002;
        attribute rippleRms : VoltageVolt = 0.001;

        port powerIn : PowerPort;
        port excitationOut : ExcitationPort;

        state def ExcitationSupplyState {
            state off;
            state ramping;
            state regulated;
            state fault;

            transition first off;
            transition off_to_ramping
                first off then ramping;

            transition ramping_to_regulated
                first ramping then regulated;

            transition regulated_to_fault
                first regulated then fault;

            transition fault_to_off
                first fault then off;
        }
    }

    part def InstrumentationAmplifier {
        attribute gain : Real = 128.0;
        attribute inputOffset : VoltageVolt = 0.00001;
        attribute commonModeRejectionRatio : Real = 100000.0;
        attribute outputSaturationVoltage : VoltageVolt = 4.85;

        port bridgeInput : AnalogInputPort;
        port amplifiedOutput : AnalogSignalPort;

        action def AmplifyBridgeSignal {
            in item bridgeSignal : AnalogVoltageSignal;
            out item amplifiedSignal : AnalogVoltageSignal;
        }
    }

    part def LowPassFilter {
        attribute cutoffFrequency : FrequencyHertz = 250.0;
        attribute order : Integer = 4;
        attribute passbandRipple : Real = 0.01;

        port filterInput : AnalogInputPort;
        port filterOutput : AnalogSignalPort;

        action def RemoveHighFrequencyNoise {
            in item noisySignal : AnalogVoltageSignal;
            out item filteredSignal : AnalogVoltageSignal;
        }
    }

    part def AnalogToDigitalConverter {
        attribute resolutionBits : Integer = 24;
        attribute referenceVoltage : VoltageVolt = 5.0;
        attribute sampleRate : FrequencyHertz = 1000.0;
        attribute quantizationNoise : VoltageVolt;

        port analogInput : AnalogInputPort;
        port digitalOutput : DigitalMeasurementPort;

        action def SampleVoltage {
            in item conditionedSignal : AnalogVoltageSignal;
            out item digitalMeasurement : DigitizedMeasurement;
        }
    }

    part def TemperatureSensor {
        attribute accuracy : TemperatureCelsius = 0.5;
        attribute updateRate : FrequencyHertz = 10.0;

        port temperatureOutput : StrainOutputPort;

        action def MeasureGaugeTemperature {
            out item temperatureMeasurement : CompensatedStrainMeasurement;
        }
    }

    part def SignalProcessor {
        attribute zeroOffset : Microstrain = 0.0;
        attribute calibrationSlope : CalibrationFactor = 1.0;
        attribute temperatureCoefficient : Real = 0.000011;
        attribute movingAverageWindow : Integer = 16;
        attribute overloadThreshold : Microstrain = 9500.0;

        port digitalInput : DigitalMeasurementPort;
        port strainOut : StrainOutputPort;
        port diagnosticOut : DiagnosticPort;

        action def ConvertVoltageToStrain {
            in item measurement : DigitizedMeasurement;
            out item compensatedStrain : CompensatedStrainMeasurement;
        }

        action def ApplyTemperatureCompensation {
            in item uncompensatedStrain : CompensatedStrainMeasurement;
            out item compensatedStrain : CompensatedStrainMeasurement;
        }

        action def EvaluateDiagnostics {
            in item measurement : DigitizedMeasurement;
            out item diagnosticStatus : DiagnosticStatus;
        }

        state def MeasurementProcessingState {
            state initializing;
            state zeroing;
            state measuring;
            state saturated;
            state fault;

            transition first initializing;
            transition initialized
                first initializing then zeroing;

            transition zero_complete
                first zeroing then measuring;

            transition overload_detected
                first measuring then saturated;

            transition signal_recovered
                first saturated then measuring;

            transition diagnostic_fault
                first measuring then fault;

            transition reset_requested
                first fault then initializing;
        }
    }

    part def StrainGaugeAssembly {
        attribute adhesiveShearStrength : Real {
            unit = "MPa";
        } = 25.0;
        attribute operatingTemperatureMin : TemperatureCelsius = -40.0;
        attribute operatingTemperatureMax : TemperatureCelsius = 125.0;
        attribute measurementRange : Microstrain = 10000.0;

        port mechanicalInput : MechanicalBondPort;
        port strainOutput : StrainOutputPort;
        port healthOutput : DiagnosticPort;
        port supplyInput : PowerPort;

        part gauge : StrainGaugeElement;
        part bridge : WheatstoneBridge;
        part excitation : ExcitationSupply;
        part amplifier : InstrumentationAmplifier;
        part filter : LowPassFilter;
        part adc : AnalogToDigitalConverter;
        part temperatureSensor : TemperatureSensor;
        part processor : SignalProcessor;

        connect mechanicalInput to gauge.substrateInterface;
        connect supplyInput to excitation.powerIn;
        connect excitation.excitationOut to bridge.excitationIn;
        connect gauge.resistanceOutput to bridge.gaugeLegIn;
        connect bridge.bridgeOut to amplifier.bridgeInput;
        connect amplifier.amplifiedOutput to filter.filterInput;
        connect filter.filterOutput to adc.analogInput;
        connect adc.digitalOutput to processor.digitalInput;
        connect processor.strainOut to strainOutput;
        connect processor.diagnosticOut to healthOutput;

        perform action senseStrain {
            first start;
            then excitation.GenerateDifferentialVoltage;
            then gauge.ConvertStrainToResistance;
            then bridge.GenerateDifferentialVoltage;
            then amplifier.AmplifyBridgeSignal;
            then filter.RemoveHighFrequencyNoise;
            then adc.SampleVoltage;
            then processor.ConvertVoltageToStrain;
            then processor.ApplyTemperatureCompensation;
            then processor.EvaluateDiagnostics;
        }
    }

    part def HostMonitoringInterface {
        attribute displayUpdateRate : FrequencyHertz = 5.0;
        attribute alarmThreshold : Microstrain = 8000.0;
        attribute loggedSampleRate : FrequencyHertz = 100.0;

        port strainInput : StrainOutputPort;
        port diagnosticInput : DiagnosticPort;

        action def DisplayAndLogStrain {
            in item measurement : CompensatedStrainMeasurement;
        }

        action def AnnunciateFault {
            in item status : DiagnosticStatus;
        }
    }

    part strainGaugeMeasurementSystem {
        attribute primaryFunction : String = "Convert mechanical deformation of a bonded structure into an accurate, temperature-compensated electrical strain measurement for monitoring load, stress, or structural health.";
        attribute systemAccuracy : Microstrain = 5.0;
        attribute endToEndLatency : Real {
            unit = "ms";
        } = 25.0;

        part sensingAssembly : StrainGaugeAssembly;
        part monitor : HostMonitoringInterface;

        port structureStrainInput : MechanicalBondPort;
        port externalPowerInput : PowerPort;
        port compensatedStrainOutput : StrainOutputPort;
        port diagnosticStatusOutput : DiagnosticPort;

        connect structureStrainInput to sensingAssembly.mechanicalInput;
        connect externalPowerInput to sensingAssembly.supplyInput;
        connect sensingAssembly.strainOutput to monitor.strainInput;
        connect sensingAssembly.healthOutput to monitor.diagnosticInput;
        connect sensingAssembly.strainOutput to compensatedStrainOutput;
        connect sensingAssembly.healthOutput to diagnosticStatusOutput;
    }

    requirement def PrimaryFunctionRequirement {
        doc /* The system shall sense mechanical strain applied to a bonded structure and provide a compensated digital strain measurement representing structural deformation. */

        subject system : StrainGaugeAssembly;

        require constraint {
            system.measurementRange >= 10000.0
        }
    }

    requirement def AccuracyRequirement {
        doc /* The system shall report compensated strain with uncertainty no greater than 5 microstrain over the normal operating range. */

        subject system : StrainGaugeMeasurementSystem::strainGaugeMeasurementSystem;

        require constraint {
            system.systemAccuracy <= 5.0
        }
    }

    requirement def LatencyRequirement {
        doc /* The system shall produce a valid compensated strain measurement within 25 milliseconds of sampled bridge voltage acquisition. */

        subject system : StrainGaugeMeasurementSystem::strainGaugeMeasurementSystem;

        require constraint {
            system.endToEndLatency <= 25.0
        }
    }

    requirement def TemperatureOperatingRequirement {
        doc /* The sensing assembly shall operate from -40 degC to 125 degC while applying temperature compensation to strain measurements. */

        subject assembly : StrainGaugeAssembly;

        require constraint {
            assembly.operatingTemperatureMin <= -40.0 and assembly.operatingTemperatureMax >= 125.0
        }
    }

    requirement def DiagnosticRequirement {
        doc /* The system shall identify open bridge, short bridge, excitation range, saturation, and calibration validity faults. */

        subject processor : SignalProcessor;

        require constraint {
            processor.overloadThreshold <= 9500.0
        }
    }

    satisfy PrimaryFunctionRequirement by strainGaugeMeasurementSystem.sensingAssembly;
    satisfy AccuracyRequirement by strainGaugeMeasurementSystem;
    satisfy LatencyRequirement by strainGaugeMeasurementSystem;
    satisfy TemperatureOperatingRequirement by strainGaugeMeasurementSystem.sensingAssembly;
    satisfy DiagnosticRequirement by strainGaugeMeasurementSystem.sensingAssembly.processor;

}

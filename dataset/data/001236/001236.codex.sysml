package ScintillometerSystemModel {

    import ScalarValues::*;
    import SI::*;

    attribute def LengthValue {
        value : Real;
        unit : LengthUnit;
    }

    attribute def AreaValue {
        value : Real;
        unit : AreaUnit;
    }

    attribute def PowerValue {
        value : Real;
        unit : PowerUnit;
    }

    attribute def WavelengthValue {
        value : Real;
        unit : LengthUnit;
    }

    attribute def FrequencyValue {
        value : Real;
        unit : FrequencyUnit;
    }

    attribute def TemperatureValue {
        value : Real;
        unit : TemperatureUnit;
    }

    attribute def VoltageValue {
        value : Real;
        unit : ElectricPotentialUnit;
    }

    attribute def RatioValue {
        value : Real;
    }

    attribute def HeatFluxValue {
        value : Real;
        unit : PowerUnit;
        perArea : AreaUnit;
    }

    item def OpticalBeam {
        attribute wavelength : WavelengthValue;
        attribute opticalPower : PowerValue;
        attribute modulationFrequency : FrequencyValue;
        attribute beamDivergence_mrad : Real;
    }

    item def PropagatedOpticalSignal {
        attribute meanIntensity : Real;
        attribute intensityVariance : Real;
        attribute scintillationIndex : RatioValue;
        attribute receivedPower : PowerValue;
    }

    item def DetectorVoltageSignal {
        attribute voltage : VoltageValue;
        attribute sampleRate : FrequencyValue;
        attribute noiseFloor : VoltageValue;
    }

    item def AtmosphericPathMeasurement {
        attribute pathLength : LengthValue;
        attribute refractiveIndexStructureParameter_Cn2 : Real;
        attribute temperatureStructureParameter_CT2 : Real;
        attribute sensibleHeatFlux : HeatFluxValue;
        attribute signalQuality : RatioValue;
    }

    item def MeteorologicalData {
        attribute airTemperature : TemperatureValue;
        attribute pressure_hPa : Real;
        attribute relativeHumidity_percent : Real;
        attribute windSpeed_mps : Real;
        attribute windDirection_deg : Real;
    }

    item def HealthStatus {
        attribute transmitterReady : Boolean;
        attribute receiverReady : Boolean;
        attribute alignmentQuality : RatioValue;
        attribute batteryStateOfCharge : RatioValue;
        attribute faultActive : Boolean;
    }

    port def OpticalTransmitPort {
        out item beam : OpticalBeam;
    }

    port def OpticalReceivePort {
        in item signal : PropagatedOpticalSignal;
    }

    port def ElectricalSignalPort {
        out item detectorSignal : DetectorVoltageSignal;
    }

    port def DataInPort {
        in item metData : MeteorologicalData;
    }

    port def MeasurementOutPort {
        out item measurement : AtmosphericPathMeasurement;
    }

    port def HealthOutPort {
        out item status : HealthStatus;
    }

    part def OpticalTransmitter {
        attribute emittedWavelength : WavelengthValue = (value = 880.0, unit = nm);
        attribute nominalOpticalPower : PowerValue = (value = 0.75, unit = W);
        attribute modulationFrequency : FrequencyValue = (value = 1000.0, unit = Hz);
        attribute beamDivergence_mrad : Real = 1.5;
        attribute apertureDiameter : LengthValue = (value = 0.15, unit = m);

        port opticalOut : OpticalTransmitPort;

        action emitBeam {
            out item beam : OpticalBeam;
            first start;
            then createBeam;
            action createBeam {
                beam.wavelength = emittedWavelength;
                beam.opticalPower = nominalOpticalPower;
                beam.modulationFrequency = modulationFrequency;
                beam.beamDivergence_mrad = beamDivergence_mrad;
            }
            then done;
        }

        state def TransmitterState {
            entry action initializeDriver;
            state Off;
            state WarmUp;
            state Emitting;
            state Fault;

            transition initial then Off;
            transition Off_to_WarmUp first Off then WarmUp
                accept PowerCommand
                if commandOn == true;

            transition WarmUp_to_Emitting first WarmUp then Emitting
                if driverTemperatureStable == true;

            transition Emitting_to_Fault first Emitting then Fault
                if laserCurrentOutOfRange == true or opticalPowerLow == true;

            transition Fault_to_Off first Fault then Off
                accept ResetCommand;
        }

        exhibit state transmitterBehavior : TransmitterState;
    }

    part def AtmosphericPropagationPath {
        attribute pathLength : LengthValue = (value = 1000.0, unit = m);
        attribute apertureSeparation : LengthValue = (value = 1000.0, unit = m);
        attribute nominalCn2 : Real = 1.0e-14;
        attribute turbulenceScale_m : Real = 0.1;

        port pathInput : OpticalReceivePort;
        port pathOutput : OpticalTransmitPort;

        action imposeScintillation {
            in item beam : OpticalBeam;
            out item signal : PropagatedOpticalSignal;

            first receiveBeam;
            then estimatePathTurbulence;
            action estimatePathTurbulence {
                signal.meanIntensity = beam.opticalPower.value / 1.0;
                signal.intensityVariance = nominalCn2 * pathLength.value * 1.0e12;
                signal.scintillationIndex.value = signal.intensityVariance / signal.meanIntensity;
                signal.receivedPower.value = beam.opticalPower.value * 0.65;
                signal.receivedPower.unit = W;
            }
            then deliverSignal;
        }
    }

    part def OpticalReceiver {
        attribute apertureDiameter : LengthValue = (value = 0.15, unit = m);
        attribute detectorResponsivity_AperW : Real = 0.55;
        attribute transimpedanceGain_ohm : Real = 100000.0;
        attribute analogBandwidth : FrequencyValue = (value = 2000.0, unit = Hz);

        port opticalIn : OpticalReceivePort;
        port detectorOut : ElectricalSignalPort;

        action convertOpticalToVoltage {
            in item signal : PropagatedOpticalSignal;
            out item detectorSignal : DetectorVoltageSignal;

            first collectLight;
            then photodetect;
            action photodetect {
                detectorSignal.voltage.value = signal.receivedPower.value * detectorResponsivity_AperW * transimpedanceGain_ohm;
                detectorSignal.voltage.unit = V;
                detectorSignal.sampleRate.value = 200.0;
                detectorSignal.sampleRate.unit = Hz;
                detectorSignal.noiseFloor.value = 0.002;
                detectorSignal.noiseFloor.unit = V;
            }
            then outputSignal;
        }

        state def ReceiverState {
            state Standby;
            state SearchingAlignment;
            state TrackingBeam;
            state Saturated;
            state Fault;

            transition initial then Standby;
            transition Standby_to_Searching first Standby then SearchingAlignment
                accept MeasurementStartCommand;

            transition Searching_to_Tracking first SearchingAlignment then TrackingBeam
                if alignmentQuality.value >= 0.80;

            transition Tracking_to_Saturated first TrackingBeam then Saturated
                if detectorSignal.voltage.value > 9.5;

            transition Saturated_to_Tracking first Saturated then TrackingBeam
                if detectorSignal.voltage.value <= 8.0;

            transition Tracking_to_Fault first TrackingBeam then Fault
                if detectorTemperatureHigh == true;
        }

        exhibit state receiverBehavior : ReceiverState;
    }

    part def SignalProcessor {
        attribute averagingPeriod_s : Real = 60.0;
        attribute minimumSignalQuality : RatioValue = (value = 0.70);
        attribute validCn2LowerBound : Real = 1.0e-18;
        attribute validCn2UpperBound : Real = 1.0e-11;

        port signalIn : ElectricalSignalPort;
        port metIn : DataInPort;
        port measurementOut : MeasurementOutPort;

        action calculateAtmosphericFlux {
            in item detectorSignal : DetectorVoltageSignal;
            in item metData : MeteorologicalData;
            out item measurement : AtmosphericPathMeasurement;

            first sampleSignal;
            then computeScintillationStatistics;
            action computeScintillationStatistics {
                measurement.pathLength.value = 1000.0;
                measurement.pathLength.unit = m;
                measurement.refractiveIndexStructureParameter_Cn2 =
                    max(validCn2LowerBound,
                        min(validCn2UpperBound,
                            detectorSignal.voltage.value * detectorSignal.voltage.value * 1.0e-15));
                measurement.temperatureStructureParameter_CT2 =
                    measurement.refractiveIndexStructureParameter_Cn2 * 8.0e5;
            }
            then computeSensibleHeatFlux;
            action computeSensibleHeatFlux {
                measurement.sensibleHeatFlux.value =
                    1200.0 * 1005.0 * 0.4 * metData.windSpeed_mps *
                    measurement.temperatureStructureParameter_CT2;
                measurement.sensibleHeatFlux.unit = W;
                measurement.sensibleHeatFlux.perArea = m^2;
                measurement.signalQuality.value =
                    max(0.0, min(1.0, detectorSignal.voltage.value / 5.0));
            }
            then publishMeasurement;
        }

        state def ProcessingState {
            state Idle;
            state Acquiring;
            state Computing;
            state Publishing;
            state InvalidData;

            transition initial then Idle;
            transition Idle_to_Acquiring first Idle then Acquiring
                accept MeasurementStartCommand;

            transition Acquiring_to_Computing first Acquiring then Computing
                if acquiredSampleCount >= requiredSampleCount;

            transition Computing_to_Publishing first Computing then Publishing
                if computedMeasurement.signalQuality.value >= minimumSignalQuality.value;

            transition Computing_to_InvalidData first Computing then InvalidData
                if computedMeasurement.signalQuality.value < minimumSignalQuality.value;

            transition Publishing_to_Acquiring first Publishing then Acquiring
                after 60 s;

            transition InvalidData_to_Acquiring first InvalidData then Acquiring
                after 10 s;
        }

        exhibit state processingBehavior : ProcessingState;
    }

    part def AlignmentSubsystem {
        attribute azimuthCommand_deg : Real;
        attribute elevationCommand_deg : Real;
        attribute alignmentQuality : RatioValue = (value = 0.0);
        attribute maximumPointingError_mrad : Real = 0.5;

        action alignOpticalPath {
            first scanAzimuth;
            then scanElevation;
            then maximizeReceivedSignal;
            action maximizeReceivedSignal {
                alignmentQuality.value = 0.92;
                azimuthCommand_deg = 12.3;
                elevationCommand_deg = 1.8;
            }
            then holdTracking;
        }

        state def AlignmentState {
            state Parked;
            state CoarseScan;
            state FineTrack;
            state LostSignal;

            transition initial then Parked;
            transition Parked_to_CoarseScan first Parked then CoarseScan
                accept AlignmentStartCommand;

            transition CoarseScan_to_FineTrack first CoarseScan then FineTrack
                if alignmentQuality.value >= 0.75;

            transition FineTrack_to_LostSignal first FineTrack then LostSignal
                if alignmentQuality.value < 0.40;

            transition LostSignal_to_CoarseScan first LostSignal then CoarseScan
                after 5 s;
        }

        exhibit state alignmentBehavior : AlignmentState;
    }

    part def PowerSubsystem {
        attribute inputVoltage : VoltageValue = (value = 24.0, unit = V);
        attribute transmitterSupplyVoltage : VoltageValue = (value = 12.0, unit = V);
        attribute electronicsSupplyVoltage : VoltageValue = (value = 5.0, unit = V);
        attribute batteryCapacity_Wh : Real = 480.0;
        attribute stateOfCharge : RatioValue = (value = 1.0);

        action distributePower {
            first validateInput;
            then energizeReceiverElectronics;
            then energizeTransmitterDriver;
            then monitorEnergyReserve;
        }
    }

    part def MeteorologicalInterface {
        port metOut : DataInPort;

        attribute updateRate : FrequencyValue = (value = 1.0, unit = Hz);

        action acquireMeteorologicalData {
            out item metData : MeteorologicalData;

            first readSensors;
            then validateSensors;
            action validateSensors {
                metData.airTemperature.value = 293.15;
                metData.airTemperature.unit = K;
                metData.pressure_hPa = 1013.25;
                metData.relativeHumidity_percent = 55.0;
                metData.windSpeed_mps = 4.0;
                metData.windDirection_deg = 225.0;
            }
            then outputMeteorology;
        }
    }

    part def HealthMonitor {
        port statusOut : HealthOutPort;

        action evaluateSystemHealth {
            in item measurement : AtmosphericPathMeasurement;
            out item status : HealthStatus;

            first collectSubsystemStatus;
            then evaluateFaults;
            action evaluateFaults {
                status.transmitterReady = true;
                status.receiverReady = true;
                status.alignmentQuality.value = 0.92;
                status.batteryStateOfCharge.value = 0.83;
                status.faultActive = measurement.signalQuality.value < 0.30;
            }
            then publishHealth;
        }
    }

    part def ScintillometerSystem {
        attribute operationalPathLength : LengthValue = (value = 1000.0, unit = m);
        attribute primaryFunction : String =
            "Measure atmospheric optical scintillation over a horizontal path and estimate turbulence intensity and sensible heat flux.";

        part transmitter : OpticalTransmitter;
        part propagationPath : AtmosphericPropagationPath;
        part receiver : OpticalReceiver;
        part processor : SignalProcessor;
        part alignment : AlignmentSubsystem;
        part power : PowerSubsystem;
        part meteorology : MeteorologicalInterface;
        part healthMonitor : HealthMonitor;

        port measurementOut : MeasurementOutPort;
        port healthOut : HealthOutPort;

        connection opticalEmission
            connect transmitter.opticalOut to propagationPath.pathInput;

        connection atmosphericOpticalLink
            connect propagationPath.pathOutput to receiver.opticalIn;

        connection receiverSignalLink
            connect receiver.detectorOut to processor.signalIn;

        connection meteorologicalDataLink
            connect meteorology.metOut to processor.metIn;

        connection measurementOutputLink
            connect processor.measurementOut to measurementOut;

        connection healthOutputLink
            connect healthMonitor.statusOut to healthOut;

        action performScintillometerMeasurement {
            first powerUp;
            action powerUp {
                perform power.distributePower;
            }

            then alignSystem;
            action alignSystem {
                perform alignment.alignOpticalPath;
            }

            then emitOpticalBeam;
            action emitOpticalBeam {
                perform transmitter.emitBeam;
            }

            then acquireReturnedSignal;
            action acquireReturnedSignal {
                perform receiver.convertOpticalToVoltage;
            }

            then computeAtmosphericMeasurement;
            action computeAtmosphericMeasurement {
                perform processor.calculateAtmosphericFlux;
            }

            then reportSystemHealth;
            action reportSystemHealth {
                perform healthMonitor.evaluateSystemHealth;
            }
        }

        state def SystemOperatingState {
            state Off;
            state Initializing;
            state Aligning;
            state Measuring;
            state Degraded;
            state Faulted;
            state Shutdown;

            transition initial then Off;

            transition Off_to_Initializing first Off then Initializing
                accept PowerOnCommand;

            transition Initializing_to_Aligning first Initializing then Aligning
                if power.stateOfCharge.value > 0.20;

            transition Aligning_to_Measuring first Aligning then Measuring
                if alignment.alignmentQuality.value >= 0.80;

            transition Measuring_to_Degraded first Measuring then Degraded
                if processor.minimumSignalQuality.value > measuredSignalQuality.value;

            transition Degraded_to_Measuring first Degraded then Measuring
                if measuredSignalQuality.value >= processor.minimumSignalQuality.value;

            transition Measuring_to_Faulted first Measuring then Faulted
                if criticalFaultDetected == true;

            transition Faulted_to_Shutdown first Faulted then Shutdown
                accept ShutdownCommand;

            transition Measuring_to_Shutdown first Measuring then Shutdown
                accept ShutdownCommand;
        }

        exhibit state systemBehavior : SystemOperatingState;
    }

    requirement def PrimaryFunctionRequirement {
        doc
            /* The scintillometer system shall transmit an optical beam across a known atmospheric path, receive the scintillated optical signal, and compute a path-averaged atmospheric turbulence measurement. */
    }

    requirement def HeatFluxEstimationRequirement {
        doc
            /* The system shall estimate sensible heat flux using optical intensity fluctuations and meteorological data when signal quality is at least 0.70. */
    }

    requirement def OpticalPathRequirement {
        doc
            /* The system shall support an operational optical path length from 250 m to 5000 m with maintained alignment quality of at least 0.80 during measurement. */
    }

    requirement def MeasurementOutputRequirement {
        doc
            /* The system shall publish refractive index structure parameter, temperature structure parameter, sensible heat flux, path length, and signal quality once per averaging period. */
    }

    requirement def HealthMonitoringRequirement {
        doc
            /* The system shall report transmitter readiness, receiver readiness, alignment quality, battery state of charge, and active fault status. */
    }

    requirement primaryFunctionReq : PrimaryFunctionRequirement {
        subject scintillometer : ScintillometerSystem;
        require constraint {
            scintillometer.primaryFunction ==
            "Measure atmospheric optical scintillation over a horizontal path and estimate turbulence intensity and sensible heat flux."
        }
    }

    requirement heatFluxReq : HeatFluxEstimationRequirement {
        subject processor : SignalProcessor;
        require constraint {
            processor.minimumSignalQuality.value >= 0.70
        }
    }

    requirement opticalPathReq : OpticalPathRequirement {
        subject system : ScintillometerSystem;
        require constraint {
            system.operationalPathLength.value >= 250.0 and
            system.operationalPathLength.value <= 5000.0
        }
    }

    requirement outputReq : MeasurementOutputRequirement {
        subject processor : SignalProcessor;
        require constraint {
            processor.averagingPeriod_s == 60.0
        }
    }

    requirement healthReq : HealthMonitoringRequirement {
        subject health : HealthMonitor;
    }

    satisfy primaryFunctionSatisfaction
        by ScintillometerSystem
        satisfy primaryFunctionReq;

    satisfy heatFluxSatisfaction
        by SignalProcessor
        satisfy heatFluxReq;

    satisfy opticalPathSatisfaction
        by ScintillometerSystem
        satisfy opticalPathReq;

    satisfy outputSatisfaction
        by SignalProcessor
        satisfy outputReq;

    satisfy healthSatisfaction
        by HealthMonitor
        satisfy healthReq;

    analysis def ScintillationMeasurementAnalysis {
        in item signal : PropagatedOpticalSignal;
        in item metData : MeteorologicalData;
        out item result : AtmosphericPathMeasurement;

        objective computeCn2 {
            doc
                /* Derive path-averaged refractive index structure parameter from normalized optical intensity variance. */
        }

        objective estimateHeatFlux {
            doc
                /* Combine turbulence estimate with air temperature, pressure, humidity, and wind speed to estimate sensible heat flux. */
        }
    }

    allocation def FunctionalAllocation {
        allocate PrimaryFunctionRequirement to ScintillometerSystem;
        allocate HeatFluxEstimationRequirement to SignalProcessor;
        allocate OpticalPathRequirement to OpticalTransmitter;
        allocate OpticalPathRequirement to OpticalReceiver;
        allocate MeasurementOutputRequirement to SignalProcessor;
        allocate HealthMonitoringRequirement to HealthMonitor;
    }

}

package HospitalBedSystemModel {

    import ScalarValues::*;
    import ISQ::*;
    import SI::*;

    attribute def Mass :> ScalarValues::Real;
    attribute def Length :> ScalarValues::Real;
    attribute def Angle :> ScalarValues::Real;
    attribute def Force :> ScalarValues::Real;
    attribute def Time :> ScalarValues::Real;
    attribute def ElectricPotential :> ScalarValues::Real;
    attribute def ElectricCurrent :> ScalarValues::Real;
    attribute def Power :> ScalarValues::Real;
    attribute def BooleanValue :> ScalarValues::Boolean;

    item def Patient {
        attribute bodyMass : Mass;
        attribute height : Length;
        attribute mobilityLimited : BooleanValue;
    }

    item def CaregiverCommand {
        attribute requestedFunction : CommandKind;
        attribute targetPosition : PositionKind;
    }

    enum def CommandKind {
        enum raiseBackrest;
        enum lowerBackrest;
        enum raiseKnees;
        enum lowerKnees;
        enum raiseBed;
        enum lowerBed;
        enum lockCasters;
        enum unlockCasters;
        enum stopMotion;
        enum emergencyCPR;
    }

    enum def PositionKind {
        enum flat;
        enum chair;
        enum lowTransfer;
        enum highCare;
        enum trendelenburg;
        enum reverseTrendelenburg;
    }

    enum def BedOperatingState {
        enum unoccupied;
        enum occupiedReady;
        enum repositioning;
        enum transportLocked;
        enum alarmActive;
        enum emergencyCPRMode;
        enum faulted;
    }

    enum def SideRailState {
        enum raised;
        enum lowered;
        enum latched;
        enum unlatched;
    }

    item def BedStatus {
        attribute bedState : BedOperatingState;
        attribute headAngle : Angle;
        attribute kneeAngle : Angle;
        attribute deckHeight : Length;
        attribute brakeApplied : BooleanValue;
        attribute sideRailsRaised : BooleanValue;
        attribute patientDetected : BooleanValue;
        attribute faultDetected : BooleanValue;
    }

    item def ElectricalEnergy {
        attribute voltage : ElectricPotential;
        attribute current : ElectricCurrent;
        attribute availablePower : Power;
    }

    item def MechanicalSupportLoad {
        attribute supportedMass : Mass;
        attribute distributedLoad : Force;
    }

    item def MotionRequest {
        attribute command : CommandKind;
        attribute targetHeadAngle : Angle;
        attribute targetKneeAngle : Angle;
        attribute targetDeckHeight : Length;
    }

    port def PatientSupportPort {
        in item patient : Patient;
        out item supportLoad : MechanicalSupportLoad;
    }

    port def CommandPort {
        in item command : CaregiverCommand;
    }

    port def StatusPort {
        out item status : BedStatus;
    }

    port def PowerPort {
        in item energy : ElectricalEnergy;
    }

    port def MotionControlPort {
        in item request : MotionRequest;
        out item status : BedStatus;
    }

    port def AlarmPort {
        out item alarmStatus : BedStatus;
    }

    part def HospitalBed {
        attribute maxPatientMass : Mass = 250.0;
        attribute nominalDeckLength : Length = 2.05;
        attribute nominalDeckWidth : Length = 0.91;
        attribute minDeckHeight : Length = 0.36;
        attribute maxDeckHeight : Length = 0.78;
        attribute maxHeadAngle : Angle = 70.0;
        attribute maxKneeAngle : Angle = 35.0;
        attribute nominalSupplyVoltage : ElectricPotential = 24.0;
        attribute maximumContinuousPower : Power = 360.0;
        attribute brakeApplied : BooleanValue = true;
        attribute patientPresent : BooleanValue = false;

        port patientSupport : PatientSupportPort;
        port caregiverInterface : CommandPort;
        port bedStatus : StatusPort;
        port powerInput : PowerPort;

        part frame : BedFrame;
        part sleepDeck : ArticulatingSleepDeck;
        part liftSystem : HeightLiftSystem;
        part sideRailAssembly : SideRailAssembly;
        part casterBrakeSystem : CasterBrakeSystem;
        part controlSystem : BedControlSystem;
        part powerSystem : BedPowerSystem;
        part patientMonitoring : PatientMonitoringSystem;
        part alarmSystem : AlarmSystem;

        connect powerInput to powerSystem.supplyInput;
        connect powerSystem.controlPowerOutput to controlSystem.powerInput;
        connect powerSystem.actuatorPowerOutput to sleepDeck.powerInput;
        connect powerSystem.actuatorPowerOutput to liftSystem.powerInput;

        connect caregiverInterface to controlSystem.commandInput;
        connect controlSystem.deckMotionOutput to sleepDeck.motionInput;
        connect controlSystem.heightMotionOutput to liftSystem.motionInput;
        connect controlSystem.brakeCommandOutput to casterBrakeSystem.commandInput;
        connect controlSystem.alarmCommandOutput to alarmSystem.alarmInput;

        connect patientSupport to sleepDeck.patientInterface;
        connect sleepDeck.deckStatusOutput to controlSystem.deckStatusInput;
        connect liftSystem.heightStatusOutput to controlSystem.heightStatusInput;
        connect sideRailAssembly.railStatusOutput to controlSystem.railStatusInput;
        connect casterBrakeSystem.brakeStatusOutput to controlSystem.brakeStatusInput;
        connect patientMonitoring.patientStatusOutput to controlSystem.patientStatusInput;
        connect controlSystem.systemStatusOutput to bedStatus;
        connect controlSystem.systemStatusOutput to alarmSystem.statusInput;

        perform action supportAndPositionPatient;
        exhibit state bedOperation;
    }

    part def BedFrame {
        attribute structuralMass : Mass = 85.0;
        attribute ratedStaticLoad : Force = 3200.0;
        attribute corrosionResistantFinish : BooleanValue = true;

        port loadInterface : PatientSupportPort;
    }

    part def ArticulatingSleepDeck {
        attribute headSectionAngle : Angle = 0.0;
        attribute kneeSectionAngle : Angle = 0.0;
        attribute footSectionAngle : Angle = 0.0;
        attribute deckLength : Length = 2.05;
        attribute deckWidth : Length = 0.91;

        port patientInterface : PatientSupportPort;
        port motionInput : MotionControlPort;
        port powerInput : PowerPort;
        port deckStatusOutput : StatusPort;

        part headActuator : LinearActuator;
        part kneeActuator : LinearActuator;
        part mattressPlatform : MattressPlatform;

        action adjustHeadSection {
            in targetAngle : Angle;
            out achievedAngle : Angle;
            first startMotion;
            then verifyAngle;
            then stopMotion;
        }

        action adjustKneeSection {
            in targetAngle : Angle;
            out achievedAngle : Angle;
            first startMotion;
            then verifyAngle;
            then stopMotion;
        }
    }

    part def MattressPlatform {
        attribute pressureRedistributionEnabled : BooleanValue = true;
        attribute mattressThickness : Length = 0.15;
        attribute cleaningCompatible : BooleanValue = true;
    }

    part def HeightLiftSystem {
        attribute currentDeckHeight : Length = 0.50;
        attribute liftStroke : Length = 0.42;
        attribute synchronizedLift : BooleanValue = true;

        port motionInput : MotionControlPort;
        port powerInput : PowerPort;
        port heightStatusOutput : StatusPort;

        part leftLiftColumn : LiftColumn;
        part rightLiftColumn : LiftColumn;

        action adjustDeckHeight {
            in targetHeight : Length;
            out achievedHeight : Length;
            first energizeLiftColumns;
            then synchronizeColumns;
            then stopAtHeight;
        }
    }

    part def LinearActuator {
        attribute ratedForce : Force = 6000.0;
        attribute strokeLength : Length = 0.25;
        attribute supplyVoltage : ElectricPotential = 24.0;
        attribute moving : BooleanValue = false;
    }

    part def LiftColumn {
        attribute ratedLiftForce : Force = 9000.0;
        attribute minimumHeight : Length = 0.36;
        attribute maximumHeight : Length = 0.78;
        attribute currentHeight : Length = 0.50;
    }

    part def SideRailAssembly {
        attribute leftHeadRailState : SideRailState = SideRailState::raised;
        attribute rightHeadRailState : SideRailState = SideRailState::raised;
        attribute leftFootRailState : SideRailState = SideRailState::raised;
        attribute rightFootRailState : SideRailState = SideRailState::raised;

        port railStatusOutput : StatusPort;

        action raiseAllRails {
            then latchRails;
            then verifyRailsRaised;
        }

        action lowerTransferRail {
            in side : ScalarValues::String;
            then releaseLatch;
            then lowerSelectedRail;
            then verifyRailLowered;
        }
    }

    part def CasterBrakeSystem {
        attribute casterDiameter : Length = 0.15;
        attribute brakeApplied : BooleanValue = true;
        attribute steeringLocked : BooleanValue = false;

        port commandInput : CommandPort;
        port brakeStatusOutput : StatusPort;

        part frontLeftCaster : Caster;
        part frontRightCaster : Caster;
        part rearLeftCaster : Caster;
        part rearRightCaster : Caster;

        action applyBrakes {
            then engageBrakeLinkage;
            then verifyBrakeApplied;
        }

        action releaseBrakes {
            then disengageBrakeLinkage;
            then verifyBrakeReleased;
        }
    }

    part def Caster {
        attribute diameter : Length = 0.15;
        attribute brakeCapable : BooleanValue = true;
        attribute locked : BooleanValue = true;
    }

    part def BedControlSystem {
        attribute motionEnabled : BooleanValue = true;
        attribute faultDetected : BooleanValue = false;
        attribute emergencyStopActive : BooleanValue = false;

        port powerInput : PowerPort;
        port commandInput : CommandPort;
        port deckMotionOutput : MotionControlPort;
        port heightMotionOutput : MotionControlPort;
        port brakeCommandOutput : CommandPort;
        port alarmCommandOutput : CommandPort;
        port deckStatusInput : StatusPort;
        port heightStatusInput : StatusPort;
        port railStatusInput : StatusPort;
        port brakeStatusInput : StatusPort;
        port patientStatusInput : StatusPort;
        port systemStatusOutput : StatusPort;

        part handPendant : CaregiverHandPendant;
        part motionController : MotionController;
        part safetyInterlockController : SafetyInterlockController;

        action processCaregiverCommand {
            in command : CaregiverCommand;
            out request : MotionRequest;
            first validateCommand;
            then checkSafetyInterlocks;
            then dispatchMotionRequest;
            then publishStatus;
        }
    }

    part def CaregiverHandPendant {
        attribute backrestControlsEnabled : BooleanValue = true;
        attribute heightControlsEnabled : BooleanValue = true;
        attribute cprButtonGuarded : BooleanValue = true;

        port commandOutput : CommandPort;
    }

    part def MotionController {
        attribute closedLoopControlEnabled : BooleanValue = true;
        attribute maximumMotionTime : Time = 30.0;

        action stopAllMotion {
            then removeActuatorPower;
            then commandBrakeHold;
            then reportStopped;
        }
    }

    part def SafetyInterlockController {
        attribute preventsMotionWhenOverloaded : BooleanValue = true;
        attribute preventsHeightMotionWhenBrakeReleased : BooleanValue = true;
        attribute requiresRailLatchConfirmation : BooleanValue = true;

        action evaluateMotionPermission {
            in requestedMotion : MotionRequest;
            out permitted : BooleanValue;
        }
    }

    part def BedPowerSystem {
        attribute mainsConnected : BooleanValue = true;
        attribute batteryBackupAvailable : BooleanValue = true;
        attribute batteryVoltage : ElectricPotential = 24.0;
        attribute batteryCapacityAmpHours : ElectricCurrent = 12.0;

        port supplyInput : PowerPort;
        port controlPowerOutput : PowerPort;
        port actuatorPowerOutput : PowerPort;

        part batteryPack : BatteryPack;
        part powerDistributionUnit : PowerDistributionUnit;
    }

    part def BatteryPack {
        attribute nominalVoltage : ElectricPotential = 24.0;
        attribute reserveOperatingTime : Time = 45.0;
        attribute chargeLevelPercent : ScalarValues::Real = 95.0;
    }

    part def PowerDistributionUnit {
        attribute overCurrentProtected : BooleanValue = true;
        attribute isolationProvided : BooleanValue = true;
        attribute maximumOutputPower : Power = 360.0;
    }

    part def PatientMonitoringSystem {
        attribute weightSensingEnabled : BooleanValue = true;
        attribute bedExitDetectionEnabled : BooleanValue = true;
        attribute overloadDetected : BooleanValue = false;

        port patientStatusOutput : StatusPort;

        part loadCells : LoadCell[4];
        part bedExitSensor : BedExitSensor;
    }

    part def LoadCell {
        attribute measuredLoad : Force = 0.0;
        attribute maximumLoad : Force = 1200.0;
    }

    part def BedExitSensor {
        attribute patientInBed : BooleanValue = false;
        attribute exitAlarmArmed : BooleanValue = true;
    }

    part def AlarmSystem {
        attribute audibleAlarmEnabled : BooleanValue = true;
        attribute visualAlarmEnabled : BooleanValue = true;
        attribute currentAlarmActive : BooleanValue = false;

        port alarmInput : CommandPort;
        port statusInput : StatusPort;
        port alarmOutput : AlarmPort;

        action announceAlarm {
            in status : BedStatus;
            then activateVisualIndicator;
            then soundAudibleAlarm;
            then publishAlarmStatus;
        }

        action silenceAlarm {
            then muteAudibleAlarm;
            then retainVisualIndicatorIfFaultPersists;
        }
    }

    action def SupportAndPositionPatient {
        in patient : Patient;
        in command : CaregiverCommand;
        out status : BedStatus;

        first acceptPatientLoad;
        then monitorPatientPresence;
        then interpretCaregiverCommand;
        then verifySafetyInterlocks;
        then repositionSleepDeckOrHeight;
        then stabilizeBed;
        then reportBedStatus;
    }

    action supportAndPositionPatient : SupportAndPositionPatient;

    state def BedOperation {
        entry action initializeControlSystem;

        state unoccupied;
        state occupiedReady;
        state repositioning;
        state transportLocked;
        state alarmActive;
        state emergencyCPRMode;
        state faulted;

        transition first unoccupied;

        transition unoccupied_to_occupiedReady
            first unoccupied
            accept patientDetected
            then occupiedReady;

        transition occupiedReady_to_repositioning
            first occupiedReady
            accept validMotionCommand
            then repositioning;

        transition repositioning_to_occupiedReady
            first repositioning
            accept targetPositionReached
            then occupiedReady;

        transition occupiedReady_to_transportLocked
            first occupiedReady
            accept brakesReleasedForTransport
            then transportLocked;

        transition transportLocked_to_occupiedReady
            first transportLocked
            accept brakesApplied
            then occupiedReady;

        transition occupiedReady_to_alarmActive
            first occupiedReady
            accept bedExitOrOverloadDetected
            then alarmActive;

        transition alarmActive_to_occupiedReady
            first alarmActive
            accept alarmCleared
            then occupiedReady;

        transition occupiedReady_to_emergencyCPRMode
            first occupiedReady
            accept emergencyCPRCommand
            then emergencyCPRMode;

        transition emergencyCPRMode_to_occupiedReady
            first emergencyCPRMode
            accept cprModeReset
            then occupiedReady;

        transition any_to_faulted
            first occupiedReady
            accept unrecoverableFaultDetected
            then faulted;
    }

    state bedOperation : BedOperation;

    requirement def PrimaryFunctionRequirement {
        doc /* The hospital bed shall support a patient safely and enable caregivers to position the patient and bed height for care, transfer, rest, transport preparation, and emergency access. */
        attribute requiredMaxPatientMass : Mass = 250.0;
        attribute requiredLowTransferHeight : Length = 0.40;
        attribute requiredHighCareHeight : Length = 0.75;
        attribute requiredHeadElevation : Angle = 65.0;

        require constraint {
            requiredMaxPatientMass <= 250.0 and
            requiredLowTransferHeight >= 0.36 and
            requiredHighCareHeight <= 0.78 and
            requiredHeadElevation <= 70.0
        }
    }

    requirement def PatientSupportRequirement {
        doc /* The hospital bed shall continuously support the patient load through the frame, sleep deck, mattress platform, and lift system without exceeding rated static load. */
        attribute requiredRatedStaticLoad : Force = 3200.0;
    }

    requirement def PositioningRequirement {
        doc /* The hospital bed shall articulate the head and knee sections and raise or lower the deck under caregiver command while maintaining controlled motion and status feedback. */
        attribute maximumHeadAngle : Angle = 70.0;
        attribute maximumKneeAngle : Angle = 35.0;
        attribute minimumDeckHeight : Length = 0.36;
        attribute maximumDeckHeight : Length = 0.78;
    }

    requirement def SafetyRequirement {
        doc /* The hospital bed shall inhibit unsafe motion, apply brakes during stationary care, detect patient exit or overload conditions, and provide audible and visual alarm indications. */
        attribute overloadProtectionRequired : BooleanValue = true;
        attribute brakeInterlockRequired : BooleanValue = true;
        attribute alarmRequired : BooleanValue = true;
    }

    requirement def EmergencyCPRRequirement {
        doc /* The hospital bed shall provide an emergency CPR mode that returns the sleep deck to a flat configuration and stops nonessential motion commands. */
        attribute cprHeadAngle : Angle = 0.0;
        attribute cprKneeAngle : Angle = 0.0;
        attribute maximumCPRTransitionTime : Time = 10.0;
    }

    requirement primaryFunction : PrimaryFunctionRequirement;
    requirement patientSupport : PatientSupportRequirement;
    requirement positioning : PositioningRequirement;
    requirement safety : SafetyRequirement;
    requirement emergencyCPR : EmergencyCPRRequirement;

    satisfy primaryFunction by HospitalBed;
    satisfy patientSupport by BedFrame;
    satisfy patientSupport by ArticulatingSleepDeck;
    satisfy positioning by ArticulatingSleepDeck;
    satisfy positioning by HeightLiftSystem;
    satisfy safety by BedControlSystem;
    satisfy safety by CasterBrakeSystem;
    satisfy safety by AlarmSystem;
    satisfy emergencyCPR by BedControlSystem;
    satisfy emergencyCPR by ArticulatingSleepDeck;

}

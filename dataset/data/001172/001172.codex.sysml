package ParkingSensorSensingUnitModel {

    import ScalarValues::*;
    import ISQ::*;
    import SI::*;

    attribute def Confidence : Real {
        :>> range = "0.0..1.0";
    }

    attribute def Distance_m : Real {
        :>> unit = SI::metre;
        :>> quantityKind = ISQ::length;
    }

    attribute def Time_s : Real {
        :>> unit = SI::second;
        :>> quantityKind = ISQ::time;
    }

    attribute def Frequency_Hz : Real {
        :>> unit = SI::hertz;
        :>> quantityKind = ISQ::frequency;
    }

    attribute def Voltage_V : Real {
        :>> unit = SI::volt;
        :>> quantityKind = ISQ::electricPotential;
    }

    attribute def Current_A : Real {
        :>> unit = SI::ampere;
        :>> quantityKind = ISQ::electricCurrent;
    }

    attribute def Temperature_C : Real {
        :>> unit = SI::degreeCelsius;
        :>> quantityKind = ISQ::thermodynamicTemperature;
    }

    attribute def SoundPressure_dB : Real {
        :>> quantityKind = ISQ::soundPressureLevel;
    }

    enum def SensorHealthKind {
        enum nominal;
        enum degraded;
        enum failed;
    }

    enum def ObstacleZoneKind {
        enum clear;
        enum caution;
        enum warning;
        enum critical;
        enum unknown;
    }

    item def ElectricalPower {
        attribute voltage : Voltage_V;
        attribute current : Current_A;
    }

    item def UltrasonicPulse {
        attribute carrierFrequency : Frequency_Hz;
        attribute emittedAt : Time_s;
        attribute pulseWidth : Time_s;
        attribute soundPressureLevel : SoundPressure_dB;
    }

    item def EchoReturn {
        attribute receivedAt : Time_s;
        attribute amplitude : SoundPressure_dB;
        attribute timeOfFlight : Time_s;
        attribute valid : Boolean;
    }

    item def DistanceMeasurement {
        attribute measuredDistance : Distance_m;
        attribute confidence : Confidence;
        attribute sampleTime : Time_s;
        attribute zone : ObstacleZoneKind;
        attribute health : SensorHealthKind;
    }

    item def DiagnosticReport {
        attribute supplyVoltage : Voltage_V;
        attribute electronicsTemperature : Temperature_C;
        attribute transducerResponsive : Boolean;
        attribute blockedFaceDetected : Boolean;
        attribute health : SensorHealthKind;
    }

    port def PowerInPort {
        in item power : ElectricalPower;
    }

    port def PulseOutPort {
        out item pulse : UltrasonicPulse;
    }

    port def EchoInPort {
        in item echo : EchoReturn;
    }

    port def DistanceOutPort {
        out item distance : DistanceMeasurement;
    }

    port def DiagnosticOutPort {
        out item diagnostic : DiagnosticReport;
    }

    port def ControlInPort {
        in attribute enable : Boolean;
        in attribute calibrationRequest : Boolean;
    }

    part def ParkingSensor {
        port powerIn : PowerInPort;
        port pulseOut : PulseOutPort;
        port echoIn : EchoInPort;
        port distanceOut : DistanceOutPort;
        port diagnosticOut : DiagnosticOutPort;
        port controlIn : ControlInPort;

        attribute minimumRange : Distance_m = 0.15;
        attribute maximumRange : Distance_m = 2.50;
        attribute cautionThreshold : Distance_m = 1.50;
        attribute warningThreshold : Distance_m = 0.75;
        attribute criticalThreshold : Distance_m = 0.30;
        attribute nominalCarrierFrequency : Frequency_Hz = 40000.0;
        attribute samplePeriod : Time_s = 0.050;
        attribute speedOfSound : Real = 343.0;
        attribute ambientTemperature : Temperature_C;
        attribute health : SensorHealthKind = SensorHealthKind::nominal;
        attribute lastMeasurement : DistanceMeasurement;

        action emitPulse {
            in attribute now : Time_s;
            out item pulse : UltrasonicPulse;

            bind pulse.carrierFrequency = nominalCarrierFrequency;
            bind pulse.emittedAt = now;
            bind pulse.pulseWidth = 0.00025;
            bind pulse.soundPressureLevel = 98.0;
        }

        action receiveEcho {
            in item echo : EchoReturn;
            out attribute accepted : Boolean;

            bind accepted = echo.valid and echo.timeOfFlight > 0.0008 and echo.timeOfFlight < 0.015;
        }

        action computeDistance {
            in item echo : EchoReturn;
            out item measurement : DistanceMeasurement;

            bind measurement.measuredDistance = echo.timeOfFlight * speedOfSound / 2.0;
            bind measurement.sampleTime = echo.receivedAt;
            bind measurement.health = health;
            bind measurement.confidence =
                if echo.valid then
                    if measurement.measuredDistance >= minimumRange and measurement.measuredDistance <= maximumRange then 0.95 else 0.35
                else
                    0.0;
            bind measurement.zone =
                if not echo.valid then
                    ObstacleZoneKind::unknown
                else if measurement.measuredDistance <= criticalThreshold then
                    ObstacleZoneKind::critical
                else if measurement.measuredDistance <= warningThreshold then
                    ObstacleZoneKind::warning
                else if measurement.measuredDistance <= cautionThreshold then
                    ObstacleZoneKind::caution
                else
                    ObstacleZoneKind::clear;
        }

        action performDiagnostics {
            in item power : ElectricalPower;
            in attribute temperature : Temperature_C;
            out item report : DiagnosticReport;

            bind report.supplyVoltage = power.voltage;
            bind report.electronicsTemperature = temperature;
            bind report.transducerResponsive = power.voltage >= 9.0 and power.voltage <= 16.0;
            bind report.blockedFaceDetected = false;
            bind report.health =
                if not report.transducerResponsive then
                    SensorHealthKind::failed
                else if temperature > 85.0 then
                    SensorHealthKind::degraded
                else
                    SensorHealthKind::nominal;
        }

        state def OperatingStateMachine {
            state off;
            state initializing;
            state idle;
            state sensing;
            state processing;
            state reporting;
            state fault;

            transition first off;

            transition enablePower
                first off
                then initializing
                accept controlIn.enable;

            transition initialized
                first initializing
                then idle;

            transition startSample
                first idle
                then sensing
                accept after samplePeriod;

            transition echoCaptured
                first sensing
                then processing
                accept echoIn.echo.valid;

            transition timeout
                first sensing
                then reporting
                accept after 0.020;

            transition processed
                first processing
                then reporting;

            transition reported
                first reporting
                then idle;

            transition diagnosticFailure
                first idle
                then fault
                if health == SensorHealthKind::failed;

            transition resetFault
                first fault
                then initializing
                accept controlIn.calibrationRequest;
        }
    }

    part def SensingUnit {
        port powerInput : PowerInPort;
        port controlInput : ControlInPort;
        port measuredDistanceOutput : DistanceOutPort;
        port diagnosticOutput : DiagnosticOutPort;

        part sensor : ParkingSensor;
        part frontBumperMount {
            attribute heightAboveGround : Distance_m = 0.48;
            attribute outwardTiltAngle_deg : Real = 0.0;
            attribute lateralOffsetFromVehicleCenter : Distance_m = 0.0;
        }

        part acousticPath {
            port emittedPulse : PulseOutPort;
            port reflectedEcho : EchoInPort;
            attribute monitoredRange : Distance_m = 2.50;
            attribute nearFieldLimit : Distance_m = 0.15;
        }

        connect powerInput.power to sensor.powerIn.power;
        connect controlInput.enable to sensor.controlIn.enable;
        connect controlInput.calibrationRequest to sensor.controlIn.calibrationRequest;
        connect sensor.distanceOut.distance to measuredDistanceOutput.distance;
        connect sensor.diagnosticOut.diagnostic to diagnosticOutput.diagnostic;
        connect sensor.pulseOut.pulse to acousticPath.emittedPulse.pulse;
        connect acousticPath.reflectedEcho.echo to sensor.echoIn.echo;

        perform action senseObstacleDistance {
            in item suppliedPower : ElectricalPower;
            in attribute enableCommand : Boolean;
            in item echo : EchoReturn;
            out item measuredDistance : DistanceMeasurement;
            out item diagnostic : DiagnosticReport;

            bind powerInput.power = suppliedPower;
            bind controlInput.enable = enableCommand;
            bind sensor.echoIn.echo = echo;
            bind measuredDistance = sensor.lastMeasurement;
            bind diagnostic.health = sensor.health;
        }
    }

    part sensingUnit : SensingUnit;

    requirement def MeasureParkingObstacleDistance {
        subject unit : SensingUnit;

        require constraint {
            unit.sensor.minimumRange <= unit.sensor.lastMeasurement.measuredDistance and
            unit.sensor.lastMeasurement.measuredDistance <= unit.sensor.maximumRange
        }

        doc /* The sensing unit shall measure obstacle distance using a parking sensor over the required parking-assist range. */
    }

    requirement def ReportObstacleZone {
        subject unit : SensingUnit;

        require constraint {
            unit.sensor.lastMeasurement.zone != ObstacleZoneKind::unknown implies
            unit.sensor.lastMeasurement.confidence >= 0.35
        }

        doc /* The sensing unit shall classify measured distance into clear, caution, warning, or critical parking zones. */
    }

    requirement def SampleRateRequirement {
        subject unit : SensingUnit;

        require constraint {
            unit.sensor.samplePeriod <= 0.100
        }

        doc /* The sensing unit shall provide distance measurements at least every 100 ms while enabled. */
    }

    requirement def DiagnosticRequirement {
        subject unit : SensingUnit;

        require constraint {
            unit.sensor.health == SensorHealthKind::nominal or
            unit.sensor.health == SensorHealthKind::degraded or
            unit.sensor.health == SensorHealthKind::failed
        }

        doc /* The sensing unit shall report parking sensor health with each distance measurement cycle. */
    }

    satisfy MeasureParkingObstacleDistance by sensingUnit;
    satisfy ReportObstacleZone by sensingUnit;
    satisfy SampleRateRequirement by sensingUnit;
    satisfy DiagnosticRequirement by sensingUnit;
}

package VariableReluctanceSensingUnitModel {

  import ScalarValues::*;
  import SI::*;

  value type MagneticFluxDensity :> Real {
    unit = "T";
  }

  value type MagneticFlux :> Real {
    unit = "Wb";
  }

  value type Reluctance :> Real {
    unit = "A/Wb";
  }

  value type Voltage :> Real {
    unit = "V";
  }

  value type Current :> Real {
    unit = "A";
  }

  value type Resistance :> Real {
    unit = "ohm";
  }

  value type Inductance :> Real {
    unit = "H";
  }

  value type Frequency :> Real {
    unit = "Hz";
  }

  value type RotationalSpeed :> Real {
    unit = "rev/min";
  }

  value type AngularPosition :> Real {
    unit = "rad";
  }

  value type Temperature :> Real {
    unit = "degC";
  }

  value type TimeDuration :> Real {
    unit = "s";
  }

  value type ToothCount :> Integer;
  value type Count :> Integer;

  item def MagneticField {
    attribute fluxDensity : MagneticFluxDensity;
    attribute flux : MagneticFlux;
  }

  item def FerromagneticToothPassage {
    attribute toothIndex : Count;
    attribute angularPosition : AngularPosition;
    attribute passageTime : TimeDuration;
  }

  item def AnalogVrSignal {
    attribute instantaneousVoltage : Voltage;
    attribute peakVoltage : Voltage;
    attribute zeroCrossingFrequency : Frequency;
  }

  item def DigitalPulse {
    attribute risingEdgeTime : TimeDuration;
    attribute period : TimeDuration;
    attribute valid : Boolean;
  }

  item def SpeedMeasurement {
    attribute speed : RotationalSpeed;
    attribute updateTime : TimeDuration;
    attribute confidence : Real;
  }

  item def DiagnosticStatus {
    attribute sensorOpenCircuit : Boolean;
    attribute sensorShortCircuit : Boolean;
    attribute signalLost : Boolean;
    attribute excessiveNoise : Boolean;
    attribute temperatureOutOfRange : Boolean;
  }

  port def MagneticPort {
    inout item field : MagneticField;
  }

  port def MechanicalTargetPort {
    in item toothPassage : FerromagneticToothPassage;
  }

  port def AnalogSignalPort {
    out item signal : AnalogVrSignal;
  }

  port def ConditionedSignalPort {
    in item rawSignal : AnalogVrSignal;
    out item pulse : DigitalPulse;
  }

  port def MeasurementPort {
    out item measurement : SpeedMeasurement;
    out item diagnostics : DiagnosticStatus;
  }

  port def PowerPort {
    in attribute supplyVoltage : Voltage;
    in attribute supplyCurrent : Current;
  }

  port def GroundPort {
    inout attribute referenceVoltage : Voltage;
  }

  part def PermanentMagnet {
    attribute remanentFluxDensity : MagneticFluxDensity = 1.20;
    attribute operatingTemperature : Temperature;
    port magneticField : MagneticPort;
  }

  part def PolePiece {
    attribute relativePermeability : Real = 4000.0;
    attribute tipDiameter : Real = 0.003;
    attribute airGap : Real = 0.0008;
    port magneticField : MagneticPort;
    port targetInterface : MechanicalTargetPort;
  }

  part def PickupCoil {
    attribute turns : Count = 1200;
    attribute windingResistance : Resistance = 650.0;
    attribute nominalInductance : Inductance = 0.180;
    attribute generatedVoltage : Voltage;
    port magneticField : MagneticPort;
    port analogOut : AnalogSignalPort;
  }

  part def ToothedWheelTarget {
    attribute toothCount : ToothCount = 60;
    attribute nominalAirGap : Real = 0.0008;
    attribute shaftSpeed : RotationalSpeed;
    port toothPassageOut : MechanicalTargetPort;
  }

  part def VariableReluctanceSensor {
    attribute minimumDetectableSpeed : RotationalSpeed = 30.0;
    attribute maximumMeasurableSpeed : RotationalSpeed = 12000.0;
    attribute outputSensitivityAt1000rpm : Voltage = 2.0;

    part magnet : PermanentMagnet;
    part polePiece : PolePiece;
    part coil : PickupCoil;

    port targetIn : MechanicalTargetPort;
    port signalOut : AnalogSignalPort;

    connect magnet.magneticField to polePiece.magneticField;
    connect polePiece.magneticField to coil.magneticField;
    connect targetIn to polePiece.targetInterface;
    connect coil.analogOut to signalOut;
  }

  part def InputProtection {
    attribute positiveClampVoltage : Voltage = 18.0;
    attribute negativeClampVoltage : Voltage = -1.0;
    attribute seriesResistance : Resistance = 10000.0;
    port rawIn : ConditionedSignalPort;
    port protectedOut : ConditionedSignalPort;
  }

  part def BandPassFilter {
    attribute lowCutFrequency : Frequency = 5.0;
    attribute highCutFrequency : Frequency = 15000.0;
    attribute gain : Real = 2.5;
    port signalIn : ConditionedSignalPort;
    port filteredOut : ConditionedSignalPort;
  }

  part def AdaptiveThresholdComparator {
    attribute hysteresisVoltage : Voltage = 0.050;
    attribute minimumPeakVoltage : Voltage = 0.080;
    port analogIn : ConditionedSignalPort;
    port pulseOut : ConditionedSignalPort;
  }

  part def Microcontroller {
    attribute timerResolution : TimeDuration = 0.000001;
    attribute pulsesPerRevolution : ToothCount = 60;
    attribute computedSpeed : RotationalSpeed;
    attribute missingToothTimeout : TimeDuration = 0.100;

    port pulseIn : ConditionedSignalPort;
    port measurementOut : MeasurementPort;
    port power : PowerPort;
    port ground : GroundPort;

    action def MeasureSpeed {
      in item pulse : DigitalPulse;
      out item speedMeasurement : SpeedMeasurement;

      action countPeriod;
      action rejectInvalidPulse;
      action computeFrequency;
      action computeRotationalSpeed;
      action publishMeasurement;

      first countPeriod then rejectInvalidPulse;
      then computeFrequency;
      then computeRotationalSpeed;
      then publishMeasurement;
    }

    state def AcquisitionStateMachine {
      state unpowered;
      state initializing;
      state waitingForSignal;
      state tracking;
      state degraded;
      state faulted;

      transition unpowered_to_initializing
        first unpowered
        then initializing
        accept when power.supplyVoltage >= 4.75;

      transition initializing_to_waiting
        first initializing
        then waitingForSignal
        accept after 0.010 [s];

      transition waiting_to_tracking
        first waitingForSignal
        then tracking
        accept when pulseIn.pulse.valid == true;

      transition tracking_to_degraded
        first tracking
        then degraded
        accept when pulseIn.pulse.period > missingToothTimeout;

      transition degraded_to_tracking
        first degraded
        then tracking
        accept when pulseIn.pulse.valid == true;

      transition any_to_faulted
        first tracking
        then faulted
        accept when measurementOut.diagnostics.sensorOpenCircuit
                 or measurementOut.diagnostics.sensorShortCircuit
                 or measurementOut.diagnostics.temperatureOutOfRange;
    }
  }

  part def PowerConditioner {
    attribute nominalInputVoltage : Voltage = 12.0;
    attribute regulatedVoltage : Voltage = 5.0;
    attribute maximumCurrent : Current = 0.100;
    port vehiclePower : PowerPort;
    port logicPower : PowerPort;
    port ground : GroundPort;
  }

  part def SensingUnit {
    attribute measuredQuantityName : String = "rotational speed";
    attribute operatingTemperatureMin : Temperature = -40.0;
    attribute operatingTemperatureMax : Temperature = 125.0;
    attribute speedAccuracyPercent : Real = 1.0;

    part target : ToothedWheelTarget;
    part sensor : VariableReluctanceSensor;
    part protection : InputProtection;
    part filter : BandPassFilter;
    part comparator : AdaptiveThresholdComparator;
    part controller : Microcontroller;
    part powerConditioner : PowerConditioner;

    port externalPower : PowerPort;
    port ground : GroundPort;
    port measurementOut : MeasurementPort;

    connect target.toothPassageOut to sensor.targetIn;
    connect sensor.signalOut to protection.rawIn;
    connect protection.protectedOut to filter.signalIn;
    connect filter.filteredOut to comparator.analogIn;
    connect comparator.pulseOut to controller.pulseIn;
    connect controller.measurementOut to measurementOut;
    connect externalPower to powerConditioner.vehiclePower;
    connect powerConditioner.logicPower to controller.power;
    connect ground to powerConditioner.ground;
    connect ground to controller.ground;
  }

  requirement def MeasureRotationalSpeedRequirement {
    subject unit : SensingUnit;

    require constraint {
      unit.measuredQuantityName == "rotational speed"
    }

    require constraint {
      unit.target.toothCount == unit.controller.pulsesPerRevolution
    }

    require constraint {
      unit.sensor.minimumDetectableSpeed <= 30.0
    }

    require constraint {
      unit.sensor.maximumMeasurableSpeed >= 12000.0
    }

    require constraint {
      unit.speedAccuracyPercent <= 1.0
    }
  }

  requirement def PassiveVrSensorRequirement {
    subject sensor : VariableReluctanceSensor;

    require constraint {
      sensor.coil.turns >= 1000
    }

    require constraint {
      sensor.coil.windingResistance >= 500.0 and sensor.coil.windingResistance <= 900.0
    }

    require constraint {
      sensor.polePiece.airGap <= 0.0010
    }
  }

  requirement def SignalConditioningRequirement {
    subject unit : SensingUnit;

    require constraint {
      unit.filter.lowCutFrequency <= 10.0
    }

    require constraint {
      unit.filter.highCutFrequency >= 10000.0
    }

    require constraint {
      unit.comparator.hysteresisVoltage >= 0.020
    }
  }

  requirement def DiagnosticRequirement {
    subject unit : SensingUnit;

    require constraint {
      unit.controller.measurementOut.diagnostics.sensorOpenCircuit == false
        and unit.controller.measurementOut.diagnostics.sensorShortCircuit == false
    }
  }

  part sensingUnit : SensingUnit;

  satisfy MeasureRotationalSpeedRequirement by sensingUnit;
  satisfy SignalConditioningRequirement by sensingUnit;
  satisfy DiagnosticRequirement by sensingUnit;
  satisfy PassiveVrSensorRequirement by sensingUnit.sensor;
}

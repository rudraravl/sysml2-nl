package PumpingSystemModel {

  import ScalarValues::*;
  import ISQ::*;

  attribute def Pressure;
  attribute def FlowRate;
  attribute def Volume;
  attribute def Temperature;
  attribute def RotationalSpeed;
  attribute def Power;
  attribute def Voltage;
  attribute def Current;
  attribute def Efficiency;

  item def Liquid {
    attribute pressure : Pressure;
    attribute temperature : Temperature;
    attribute volumetricFlow : FlowRate;
    attribute contaminationLevel : Real;
  }

  item def ElectricalPower {
    attribute voltage : Voltage;
    attribute current : Current;
    attribute power : Power;
    attribute frequency : Real;
  }

  item def ControlSignal {
    attribute command : PumpCommandKind;
    attribute requestedFlow : FlowRate;
    attribute requestedPressure : Pressure;
  }

  item def Telemetry {
    attribute measuredFlow : FlowRate;
    attribute measuredInletPressure : Pressure;
    attribute measuredOutletPressure : Pressure;
    attribute motorSpeed : RotationalSpeed;
    attribute motorCurrent : Current;
    attribute faultCode : FaultKind;
  }

  enum def PumpCommandKind {
    enum idle;
    enum start;
    enum stop;
    enum regulate;
    enum emergencyStop;
    enum reset;
  }

  enum def FaultKind {
    enum none;
    enum dryRun;
    enum overPressure;
    enum overTemperature;
    enum motorOverload;
    enum blockedFilter;
    enum sensorFailure;
  }

  port def LiquidInletPort {
    in item liquidIn : Liquid;
  }

  port def LiquidOutletPort {
    out item liquidOut : Liquid;
  }

  port def PowerInputPort {
    in item electricalPower : ElectricalPower;
  }

  port def ControlInputPort {
    in item controlSignal : ControlSignal;
  }

  port def TelemetryOutputPort {
    out item telemetry : Telemetry;
  }

  part def PumpingSystem {
    attribute designFlowRate : FlowRate = 0.025;
    attribute designOutletPressure : Pressure = 600000.0;
    attribute maximumOutletPressure : Pressure = 750000.0;
    attribute minimumInletPressure : Pressure = 120000.0;
    attribute maximumLiquidTemperature : Temperature = 353.15;
    attribute nominalElectricalPower : Power = 5500.0;
    attribute minimumHydraulicEfficiency : Efficiency = 0.72;

    port inlet : LiquidInletPort;
    port outlet : LiquidOutletPort;
    port powerInput : PowerInputPort;
    port commandInput : ControlInputPort;
    port telemetryOutput : TelemetryOutputPort;

    part suctionManifold : SuctionManifold;
    part inletFilter : InletFilter;
    part pumpAssembly : CentrifugalPumpAssembly;
    part dischargeManifold : DischargeManifold;
    part checkValve : CheckValve;
    part pressureReliefValve : PressureReliefValve;
    part controller : PumpController;
    part sensorSet : SensorSet;
    part frame : SupportFrame;

    connect inlet to suctionManifold.externalInlet;
    connect suctionManifold.filteredOutlet to inletFilter.inlet;
    connect inletFilter.outlet to pumpAssembly.hydraulicInlet;
    connect pumpAssembly.hydraulicOutlet to dischargeManifold.pumpInlet;
    connect dischargeManifold.systemOutlet to checkValve.inlet;
    connect checkValve.outlet to outlet;
    connect dischargeManifold.reliefOutlet to pressureReliefValve.inlet;
    connect pressureReliefValve.returnOutlet to suctionManifold.returnInlet;

    connect powerInput to pumpAssembly.motorPower;
    connect commandInput to controller.commandInput;
    connect sensorSet.telemetryOutput to controller.telemetryInput;
    connect controller.motorCommandOutput to pumpAssembly.motorCommand;
    connect controller.telemetryOutput to telemetryOutput;

    perform action pumpLiquid;
    exhibit state pumpingOperationalState;
  }

  part def SuctionManifold {
    port externalInlet : LiquidInletPort;
    port returnInlet : LiquidInletPort;
    port filteredOutlet : LiquidOutletPort;
    attribute internalVolume : Volume = 0.018;
    attribute allowablePressureLoss : Pressure = 12000.0;
  }

  part def InletFilter {
    port inlet : LiquidInletPort;
    port outlet : LiquidOutletPort;
    attribute meshRatingMicrometre : Real = 250.0;
    attribute cleanPressureDrop : Pressure = 5000.0;
    attribute blockedPressureDropLimit : Pressure = 30000.0;
  }

  part def CentrifugalPumpAssembly {
    port hydraulicInlet : LiquidInletPort;
    port hydraulicOutlet : LiquidOutletPort;
    port motorPower : PowerInputPort;
    port motorCommand : ControlInputPort;

    part impeller : Impeller;
    part volute : VoluteCasing;
    part shaft : DriveShaft;
    part seal : MechanicalSeal;
    part motor : ElectricMotor;

    attribute ratedFlowRate : FlowRate = 0.025;
    attribute ratedHeadPressure : Pressure = 600000.0;
    attribute ratedSpeed : RotationalSpeed = 2900.0;
    attribute hydraulicEfficiency : Efficiency = 0.78;

    connect hydraulicInlet to volute.inlet;
    connect volute.outlet to hydraulicOutlet;
    connect motor.rotorOutput to shaft.motorEnd;
    connect shaft.pumpEnd to impeller.shaftInterface;
  }

  part def Impeller {
    port shaftInterface;
    attribute outerDiameter : Real = 0.18;
    attribute bladeCount : Integer = 6;
    attribute nominalSpeed : RotationalSpeed = 2900.0;
  }

  part def VoluteCasing {
    port inlet : LiquidInletPort;
    port outlet : LiquidOutletPort;
    attribute casingPressureRating : Pressure = 1000000.0;
    attribute casingVolume : Volume = 0.012;
  }

  part def DriveShaft {
    port motorEnd;
    port pumpEnd;
    attribute diameter : Real = 0.028;
    attribute maximumTorqueNewtonMetre : Real = 42.0;
  }

  part def MechanicalSeal {
    attribute leakageLimitLitresPerHour : Real = 0.05;
    attribute maximumSealTemperature : Temperature = 363.15;
  }

  part def ElectricMotor {
    port rotorOutput;
    attribute ratedPower : Power = 5500.0;
    attribute ratedVoltage : Voltage = 480.0;
    attribute ratedCurrent : Current = 11.8;
    attribute ratedSpeed : RotationalSpeed = 2900.0;
    attribute maximumWindingTemperature : Temperature = 403.15;
  }

  part def DischargeManifold {
    port pumpInlet : LiquidInletPort;
    port systemOutlet : LiquidOutletPort;
    port reliefOutlet : LiquidOutletPort;
    attribute internalVolume : Volume = 0.015;
    attribute allowablePressureLoss : Pressure = 15000.0;
  }

  part def CheckValve {
    port inlet : LiquidInletPort;
    port outlet : LiquidOutletPort;
    attribute crackingPressure : Pressure = 8000.0;
    attribute reverseLeakageLimit : FlowRate = 0.00002;
  }

  part def PressureReliefValve {
    port inlet : LiquidInletPort;
    port returnOutlet : LiquidOutletPort;
    attribute openingPressure : Pressure = 720000.0;
    attribute reseatPressure : Pressure = 650000.0;
    attribute reliefCapacity : FlowRate = 0.04;
  }

  part def PumpController {
    port commandInput : ControlInputPort;
    port telemetryInput : TelemetryOutputPort;
    port motorCommandOutput : ControlInputPort;
    port telemetryOutput : TelemetryOutputPort;

    attribute targetFlowRate : FlowRate = 0.025;
    attribute targetOutletPressure : Pressure = 600000.0;
    attribute controlCycleTimeSeconds : Real = 0.05;
    attribute proportionalGain : Real = 1.4;
    attribute integralGain : Real = 0.3;

    perform action regulatePump;
  }

  part def SensorSet {
    port telemetryOutput : TelemetryOutputPort;

    part inletPressureSensor : PressureSensor {
      attribute measurementRangeMaximum : Pressure = 1000000.0;
      attribute accuracyPercentFullScale : Real = 0.5;
    }

    part outletPressureSensor : PressureSensor {
      attribute measurementRangeMaximum : Pressure = 1600000.0;
      attribute accuracyPercentFullScale : Real = 0.5;
    }

    part flowMeter : FlowSensor {
      attribute measurementRangeMaximum : FlowRate = 0.06;
      attribute accuracyPercentReading : Real = 1.0;
    }

    part temperatureSensor : TemperatureSensor {
      attribute measurementRangeMaximum : Temperature = 423.15;
      attribute accuracyKelvin : Real = 1.0;
    }

    part motorCurrentSensor : CurrentSensor {
      attribute measurementRangeMaximum : Current = 30.0;
      attribute accuracyPercentFullScale : Real = 1.0;
    }
  }

  part def PressureSensor {
    attribute measurementRangeMaximum : Pressure;
    attribute accuracyPercentFullScale : Real;
  }

  part def FlowSensor {
    attribute measurementRangeMaximum : FlowRate;
    attribute accuracyPercentReading : Real;
  }

  part def TemperatureSensor {
    attribute measurementRangeMaximum : Temperature;
    attribute accuracyKelvin : Real;
  }

  part def CurrentSensor {
    attribute measurementRangeMaximum : Current;
    attribute accuracyPercentFullScale : Real;
  }

  part def SupportFrame {
    attribute maximumStaticLoadNewton : Real = 2200.0;
    attribute vibrationLimitMillimetrePerSecond : Real = 4.5;
    attribute corrosionProtectionClass : String = "C4";
  }

  action def PumpLiquid {
    in item sourceLiquid : Liquid;
    in attribute commandedFlow : FlowRate;
    out item pressurizedLiquid : Liquid;

    first startMotor;
    then accelerateImpeller;
    then drawLiquidFromInlet;
    then increaseLiquidPressure;
    then dischargeLiquidToOutlet;

    action startMotor;
    action accelerateImpeller;
    action drawLiquidFromInlet;
    action increaseLiquidPressure;
    action dischargeLiquidToOutlet;
  }

  action def RegulatePump {
    in item command : ControlSignal;
    in item feedback : Telemetry;
    out item motorCommand : ControlSignal;

    first compareMeasuredAndTargetValues;
    then calculateSpeedCorrection;
    then limitCommandWithinSafeEnvelope;
    then issueMotorCommand;

    action compareMeasuredAndTargetValues;
    action calculateSpeedCorrection;
    action limitCommandWithinSafeEnvelope;
    action issueMotorCommand;
  }

  state def PumpingOperationalState {
    state off;
    state standby;
    state priming;
    state running;
    state regulating;
    state faulted;
    state emergencyStopped;

    entry action initializeTelemetry;
    action initializeTelemetry;

    transition first off then standby
      accept ControlSignal
      if command == PumpCommandKind::reset;

    transition standby then priming
      accept ControlSignal
      if command == PumpCommandKind::start;

    transition priming then running
      if measuredInletPressure >= 120000.0;

    transition running then regulating
      accept ControlSignal
      if command == PumpCommandKind::regulate;

    transition regulating then running
      accept ControlSignal
      if command == PumpCommandKind::start;

    transition running then standby
      accept ControlSignal
      if command == PumpCommandKind::stop;

    transition regulating then standby
      accept ControlSignal
      if command == PumpCommandKind::stop;

    transition standby then off
      accept ControlSignal
      if command == PumpCommandKind::stop;

    transition running then faulted
      if measuredOutletPressure > 750000.0;

    transition regulating then faulted
      if measuredInletPressure < 120000.0;

    transition running then faulted
      if motorCurrent > 18.0;

    transition faulted then standby
      accept ControlSignal
      if command == PumpCommandKind::reset;

    transition off then emergencyStopped
      accept ControlSignal
      if command == PumpCommandKind::emergencyStop;

    transition standby then emergencyStopped
      accept ControlSignal
      if command == PumpCommandKind::emergencyStop;

    transition priming then emergencyStopped
      accept ControlSignal
      if command == PumpCommandKind::emergencyStop;

    transition running then emergencyStopped
      accept ControlSignal
      if command == PumpCommandKind::emergencyStop;

    transition regulating then emergencyStopped
      accept ControlSignal
      if command == PumpCommandKind::emergencyStop;

    transition faulted then emergencyStopped
      accept ControlSignal
      if command == PumpCommandKind::emergencyStop;
  }

  requirement def PrimaryFunctionRequirement {
    doc /* The pumping system shall transfer liquid from a low-pressure inlet to a higher-pressure outlet at a controlled flow rate. */
    subject pumpingSystem : PumpingSystem;
    require constraint {
      pumpingSystem.designFlowRate >= 0.025 and
      pumpingSystem.designOutletPressure >= 600000.0
    }
  }

  requirement def FlowControlRequirement {
    doc /* The pumping system shall maintain delivered flow within plus or minus five percent of the commanded flow during normal regulating operation. */
    subject pumpingSystem : PumpingSystem;
    require constraint {
      pumpingSystem.designFlowRate >= 0.02375 and
      pumpingSystem.designFlowRate <= 0.02625
    }
  }

  requirement def PressureSafetyRequirement {
    doc /* The pumping system shall prevent outlet pressure from exceeding the maximum safe pressure by opening a relief path back to the suction side. */
    subject pumpingSystem : PumpingSystem;
    require constraint {
      pumpingSystem.maximumOutletPressure <= 750000.0 and
      pumpingSystem.pressureReliefValve.openingPressure <= 720000.0
    }
  }

  requirement def DryRunProtectionRequirement {
    doc /* The pumping system shall stop pumping and enter a faulted state when inlet pressure indicates insufficient liquid supply. */
    subject pumpingSystem : PumpingSystem;
    require constraint {
      pumpingSystem.minimumInletPressure >= 120000.0
    }
  }

  requirement def ThermalProtectionRequirement {
    doc /* The pumping system shall identify excessive liquid or motor temperature and prevent continued operation outside thermal limits. */
    subject pumpingSystem : PumpingSystem;
    require constraint {
      pumpingSystem.maximumLiquidTemperature <= 353.15 and
      pumpingSystem.pumpAssembly.motor.maximumWindingTemperature <= 403.15
    }
  }

  requirement def EfficiencyRequirement {
    doc /* The pumping system shall convert electrical input power to hydraulic output power with a minimum nominal hydraulic efficiency of seventy-two percent. */
    subject pumpingSystem : PumpingSystem;
    require constraint {
      pumpingSystem.minimumHydraulicEfficiency >= 0.72
    }
  }

  requirement def TelemetryRequirement {
    doc /* The pumping system shall provide flow, inlet pressure, outlet pressure, motor speed, motor current, and fault status telemetry to supervisory equipment. */
    subject pumpingSystem : PumpingSystem;
    require constraint {
      pumpingSystem.controller.controlCycleTimeSeconds <= 0.05
    }
  }

  requirement def BackflowPreventionRequirement {
    doc /* The pumping system shall limit reverse flow from the outlet to the inlet when the pump is stopped. */
    subject pumpingSystem : PumpingSystem;
    require constraint {
      pumpingSystem.checkValve.reverseLeakageLimit <= 0.00002
    }
  }

  requirement def MaintainabilityRequirement {
    doc /* The pumping system shall use a serviceable inlet filter and mechanical seal to support inspection and replacement without replacing the complete pump assembly. */
    subject pumpingSystem : PumpingSystem;
    require constraint {
      pumpingSystem.inletFilter.meshRatingMicrometre <= 250.0 and
      pumpingSystem.pumpAssembly.seal.leakageLimitLitresPerHour <= 0.05
    }
  }

  part pumpingStation : PumpingSystem;

  satisfy PrimaryFunctionRequirement by pumpingStation;
  satisfy FlowControlRequirement by pumpingStation.controller;
  satisfy PressureSafetyRequirement by pumpingStation.pressureReliefValve;
  satisfy DryRunProtectionRequirement by pumpingStation.controller;
  satisfy ThermalProtectionRequirement by pumpingStation.sensorSet;
  satisfy EfficiencyRequirement by pumpingStation.pumpAssembly;
  satisfy TelemetryRequirement by pumpingStation.sensorSet;
  satisfy BackflowPreventionRequirement by pumpingStation.checkValve;
  satisfy MaintainabilityRequirement by pumpingStation.inletFilter;

}

package JoblessRecoveryModel {

  import ScalarValues::*;
  import Quantities::*;
  import ISQ::*;
  import SI::*;

  attribute def Percent :> Real;
  attribute def IndexPoint :> Real;
  attribute def CurrencyUSD :> Real;
  attribute def Jobs :> Integer;
  attribute def Months :> Real;

  item def EconomicIndicator {
    attribute observationTime : String;
    attribute confidence : Percent;
  }

  item def GDPGrowthSignal :> EconomicIndicator {
    attribute quarterlyGrowthRate : Percent;
    attribute annualizedGrowthRate : Percent;
  }

  item def LaborMarketSignal :> EconomicIndicator {
    attribute unemploymentRate : Percent;
    attribute laborForceParticipationRate : Percent;
    attribute payrollJobChange : Jobs;
    attribute averageHoursWorked : Real;
  }

  item def ProductivitySignal :> EconomicIndicator {
    attribute outputPerWorkerIndex : IndexPoint;
    attribute automationInvestmentIndex : IndexPoint;
  }

  item def PolicyIntervention {
    attribute fiscalStimulusAmount : CurrencyUSD;
    attribute retrainingCapacity : Jobs;
    attribute hiringCreditRate : Percent;
    attribute targetSector : String;
  }

  item def RecoveryAssessment {
    attribute gdpRecovered : Boolean;
    attribute employmentRecovered : Boolean;
    attribute joblessRecoveryDetected : Boolean;
    attribute severityScore : IndexPoint;
    attribute primaryFinding : String;
  }

  port def IndicatorInputPort {
    in item gdp : GDPGrowthSignal;
    in item labor : LaborMarketSignal;
    in item productivity : ProductivitySignal;
  }

  port def AssessmentOutputPort {
    out item assessment : RecoveryAssessment;
  }

  port def PolicyPort {
    out item intervention : PolicyIntervention;
  }

  port def DataExchangePort {
    in item rawIndicator : EconomicIndicator;
    out item normalizedIndicator : EconomicIndicator;
  }

  action def NormalizeEconomicData {
    in item rawGDP : GDPGrowthSignal;
    in item rawLabor : LaborMarketSignal;
    in item rawProductivity : ProductivitySignal;
    out item normalizedGDP : GDPGrowthSignal;
    out item normalizedLabor : LaborMarketSignal;
    out item normalizedProductivity : ProductivitySignal;
  }

  action def DetectJoblessRecovery {
    in item gdpSignal : GDPGrowthSignal;
    in item laborSignal : LaborMarketSignal;
    in item productivitySignal : ProductivitySignal;
    out item assessment : RecoveryAssessment;

    attribute gdpRecoveryThreshold : Percent = 2.0;
    attribute unemploymentImprovementThreshold : Percent = 0.5;
    attribute payrollGrowthThreshold : Jobs = 150000;
    attribute productivityPressureThreshold : IndexPoint = 105.0;
  }

  action def SelectPolicyResponse {
    in item assessment : RecoveryAssessment;
    out item intervention : PolicyIntervention;

    attribute minimumSeverityForAction : IndexPoint = 60.0;
  }

  state def RecoveryMonitoringStateMachine {
    entry action NormalizeEconomicData;

    state CollectingIndicators;
    state EvaluatingRecovery;
    state NormalGrowthRecovery;
    state JoblessRecovery;
    state PolicyResponseActive;
    state LaborRecoveryConfirmed;

    transition first CollectingIndicators;

    transition CollectingIndicators_to_EvaluatingRecovery
      first CollectingIndicators
      then EvaluatingRecovery;

    transition EvaluatingRecovery_to_NormalGrowthRecovery
      first EvaluatingRecovery
      then NormalGrowthRecovery
      if assessment.gdpRecovered and assessment.employmentRecovered;

    transition EvaluatingRecovery_to_JoblessRecovery
      first EvaluatingRecovery
      then JoblessRecovery
      if assessment.gdpRecovered and not assessment.employmentRecovered;

    transition JoblessRecovery_to_PolicyResponseActive
      first JoblessRecovery
      then PolicyResponseActive
      if assessment.severityScore >= 60.0;

    transition PolicyResponseActive_to_LaborRecoveryConfirmed
      first PolicyResponseActive
      then LaborRecoveryConfirmed
      if assessment.employmentRecovered;

    transition LaborRecoveryConfirmed_to_CollectingIndicators
      first LaborRecoveryConfirmed
      then CollectingIndicators;
  }

  part def EconomicDataProvider {
    port dataPort : DataExchangePort;

    part nationalAccountsFeed {
      attribute publicationLag : Months = 1.0;
      attribute sourceName : String = "National Accounts";
    }

    part laborStatisticsFeed {
      attribute publicationLag : Months = 0.5;
      attribute sourceName : String = "Labor Statistics";
    }

    part productivityFeed {
      attribute publicationLag : Months = 1.5;
      attribute sourceName : String = "Productivity Survey";
    }
  }

  part def JoblessRecoveryAnalyzer {
    port indicators : IndicatorInputPort;
    port result : AssessmentOutputPort;

    part gdpRecoveryEvaluator {
      attribute minimumSustainedGrowth : Percent = 2.0;
      attribute confirmationWindow : Months = 6.0;
    }

    part employmentGapEvaluator {
      attribute maximumUnemploymentImprovementGap : Percent = 0.5;
      attribute minimumPayrollGrowth : Jobs = 150000;
      attribute confirmationWindow : Months = 6.0;
    }

    part productivityDisplacementEvaluator {
      attribute automationSensitivityThreshold : IndexPoint = 105.0;
      attribute outputWorkerDivergenceThreshold : Percent = 3.0;
    }

    perform action DetectJoblessRecovery;
  }

  part def PolicyResponsePlanner {
    port assessmentInput : AssessmentOutputPort;
    port policyOutput : PolicyPort;

    part fiscalPlanner {
      attribute maximumStimulusAmount : CurrencyUSD = 500000000000.0;
      attribute preferredHiringCreditRate : Percent = 12.0;
    }

    part workforcePlanner {
      attribute retrainingSeatCapacity : Jobs = 2500000;
      attribute placementTargetRate : Percent = 70.0;
    }

    part sectorTargetingPlanner {
      attribute prioritySectors : String = "healthcare, infrastructure, advanced manufacturing, clean energy";
      attribute minimumRegionalUnemploymentRate : Percent = 6.5;
    }

    perform action SelectPolicyResponse;
  }

  part def JoblessRecoverySystem {
    doc /* Primary function: monitor a macroeconomic recovery in which output grows while employment remains weak, identify the structural gap between GDP recovery and labor-market recovery, and recommend targeted policy responses. */

    port indicatorInputs : IndicatorInputPort;
    port assessmentOutputs : AssessmentOutputPort;
    port policyOutputs : PolicyPort;

    part dataProvider : EconomicDataProvider;
    part analyzer : JoblessRecoveryAnalyzer;
    part planner : PolicyResponsePlanner;

    connect dataProvider.dataPort.normalizedIndicator to indicatorInputs;
    connect indicatorInputs to analyzer.indicators;
    connect analyzer.result to assessmentOutputs;
    connect assessmentOutputs to planner.assessmentInput;
    connect planner.policyOutput to policyOutputs;

    exhibit stateMachine : RecoveryMonitoringStateMachine;
  }

  requirement def DetectJoblessRecoveryRequirement {
    subject system : JoblessRecoverySystem;

    require constraint {
      system.analyzer.gdpRecoveryEvaluator.minimumSustainedGrowth >= 2.0
    }

    doc /* The system shall detect a jobless recovery when GDP growth is sustained while unemployment, payroll employment, and labor-force participation fail to recover within the configured confirmation window. */
  }

  requirement def ExplainPrimaryFunctionRequirement {
    subject system : JoblessRecoverySystem;

    doc /* The system shall represent the high-level economic function of distinguishing output recovery from employment recovery and producing an actionable recovery assessment. */
  }

  requirement def PolicyRecommendationRequirement {
    subject system : JoblessRecoverySystem;

    require constraint {
      system.planner.workforcePlanner.placementTargetRate >= 65.0
    }

    doc /* The system shall generate policy interventions that prioritize employment absorption, workforce retraining, hiring incentives, and sector-specific labor demand creation. */
  }

  requirement def DataQualityRequirement {
    subject provider : EconomicDataProvider;

    require constraint {
      provider.nationalAccountsFeed.publicationLag <= 2.0 and
      provider.laborStatisticsFeed.publicationLag <= 1.0 and
      provider.productivityFeed.publicationLag <= 2.0
    }

    doc /* The system shall use timely GDP, labor-market, and productivity indicators to avoid delayed recognition of a jobless recovery. */
  }

  satisfy DetectJoblessRecoveryRequirement by JoblessRecoverySystem;
  satisfy ExplainPrimaryFunctionRequirement by JoblessRecoverySystem;
  satisfy PolicyRecommendationRequirement by JoblessRecoverySystem;
  satisfy DataQualityRequirement by EconomicDataProvider;

}

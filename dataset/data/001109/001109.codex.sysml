package IonizationGaugeModel {

  import ScalarValues::*;
  import SI::*;

  unit torr {
    conversionFactor = 133.322368;
    quantityKind = Pressure;
  }

  value type ElectricPotential {
    unit = V;
    quantityKind = Voltage;
  }

  value type ElectricCurrent {
    unit = A;
    quantityKind = ElectricCurrent;
  }

  value type PressureValue {
    unit = Pa;
    quantityKind = Pressure;
  }

  value type TemperatureValue {
    unit = K;
    quantityKind = ThermodynamicTemperature;
  }

  value type TimeValue {
    unit = s;
    quantityKind = Time;
  }

  value type SensitivityValue {
    unit = A / Pa;
  }

  value type EmissionCurrentValue {
    unit = mA;
  }

  value type DegasPowerValue {
    unit = W;
  }

  item def GasMolecule {
    attribute species : String;
    attribute ionizationPotential : ElectricPotential;
  }

  item def NeutralGasSample {
    attribute estimatedPressure : PressureValue;
    attribute temperature : TemperatureValue;
    attribute dominantSpecies : String;
  }

  item def ElectronStream {
    attribute emissionCurrent : EmissionCurrentValue;
    attribute electronEnergy : ElectricPotential;
  }

  item def PositiveIonStream {
    attribute ionCurrent : ElectricCurrent;
    attribute collectionEfficiency : Real;
  }

  item def PressureMeasurement {
    attribute pressure : PressureValue;
    attribute pressureInTorr : Real;
    attribute timestamp : TimeValue;
    attribute valid : Boolean;
    attribute uncertaintyPercent : Real;
  }

  item def GaugeCommand {
    attribute commandId : String;
    attribute requestedFilamentOn : Boolean;
    attribute requestedDegas : Boolean;
    attribute requestedZeroAdjust : Boolean;
  }

  item def GaugeStatus {
    attribute operatingMode : String;
    attribute filamentHealthy : Boolean;
    attribute highVoltageReady : Boolean;
    attribute pressureValid : Boolean;
    attribute faultCode : String;
  }

  port def VacuumPort {
    in item sampledGas : NeutralGasSample;
  }

  port def ElectronEmissionPort {
    out item electrons : ElectronStream;
  }

  port def IonCollectionPort {
    in item ions : PositiveIonStream;
  }

  port def MeasurementOutputPort {
    out item measurement : PressureMeasurement;
    out item status : GaugeStatus;
  }

  port def CommandInputPort {
    in item command : GaugeCommand;
  }

  port def PowerInputPort {
    in attribute supplyVoltage : ElectricPotential;
    in attribute availablePower : DegasPowerValue;
  }

  port def ControlSignalPort {
    in item command : GaugeCommand;
    out item status : GaugeStatus;
  }

  requirement def PrimaryFunctionRequirement {
    subject system : IonizationGaugeSystem;
    doc
    /*
     * The system shall provide a high-vacuum pressure measurement by ionizing
     * residual gas molecules in a vacuum envelope and deriving pressure from
     * the collected positive ion current.
     */
    require constraint {
      system.reportedPressure >= 1.0e-7 [Pa] and
      system.reportedPressure <= 1.0e1 [Pa]
    }
  }

  requirement def IonCurrentMeasurementRequirement {
    subject collector : IonCollector;
    doc
    /*
     * The ion collector shall measure positive ion current generated by
     * electron impact ionization with sufficient resolution for high-vacuum
     * pressure estimation.
     */
    require constraint {
      collector.minimumDetectableCurrent <= 1.0e-12 [A]
    }
  }

  requirement def FilamentProtectionRequirement {
    subject controller : GaugeController;
    doc
    /*
     * The controller shall remove filament power when measured pressure
     * exceeds the safe operating pressure limit.
     */
    require constraint {
      controller.filamentCutoffPressure <= 1.0e1 [Pa]
    }
  }

  requirement def DegasRequirement {
    subject gauge : IonizationGauge;
    doc
    /*
     * The gauge shall provide a controlled degas mode to reduce adsorbed gas
     * from internal electrodes before precision measurement.
     */
    require constraint {
      gauge.degasAssembly.maximumDegasPower >= 20.0 [W]
    }
  }

  action def IonizeGas {
    in item gas : NeutralGasSample;
    in item electrons : ElectronStream;
    out item ions : PositiveIonStream;

    attribute ionizationEfficiency : Real;
    attribute electronEnergy : ElectricPotential = 70.0 [V];

    satisfy PrimaryFunctionRequirement;
  }

  action def CollectIonCurrent {
    in item ions : PositiveIonStream;
    out attribute measuredIonCurrent : ElectricCurrent;

    attribute electrometerInputBias : ElectricPotential = 0.0 [V];
    attribute integrationTime : TimeValue = 0.100 [s];

    satisfy IonCurrentMeasurementRequirement;
  }

  action def CalculatePressure {
    in attribute ionCurrent : ElectricCurrent;
    in attribute emissionCurrent : EmissionCurrentValue;
    in attribute sensitivity : SensitivityValue;
    out item measurement : PressureMeasurement;

    attribute pressureEquation : String = "pressure = ionCurrent / (sensitivity * emissionCurrent)";
  }

  action def MeasureVacuumPressure {
    in item gas : NeutralGasSample;
    out item measurement : PressureMeasurement;

    part emitElectrons : ElectronStream;
    part generatedIons : PositiveIonStream;

    action ionize : IonizeGas {
      in gas = gas;
      in electrons = emitElectrons;
      out ions = generatedIons;
    }

    action collect : CollectIonCurrent {
      in ions = generatedIons;
    }

    action compute : CalculatePressure {
      in ionCurrent = collect.measuredIonCurrent;
    }
  }

  state def GaugeOperationalState {
    entry action initializeElectronics;
    exit action storeLastMeasurement;

    state Off;
    state Standby;
    state EmissionStabilizing;
    state Measuring;
    state Degassing;
    state Fault;

    transition initial then Off;

    transition powerApplied
      first Off
      then Standby;

    transition enableFilament
      first Standby
      then EmissionStabilizing;

    transition emissionStable
      first EmissionStabilizing
      then Measuring;

    transition requestDegas
      first Standby
      then Degassing;

    transition degasComplete
      first Degassing
      then Standby;

    transition overPressure
      first Measuring
      then Fault;

    transition filamentFailure
      first EmissionStabilizing
      then Fault;

    transition resetFault
      first Fault
      then Standby;

    transition powerRemoved
      first Standby
      then Off;
  }

  part def FilamentAssembly {
    port electronOutput : ElectronEmissionPort;

    attribute filamentVoltage : ElectricPotential = 3.0 [V];
    attribute emissionCurrentSetpoint : EmissionCurrentValue = 1.0 [mA];
    attribute electronEnergy : ElectricPotential = 70.0 [V];
    attribute healthy : Boolean = true;

    perform action emitElectrons {
      out item electronOutput.electrons : ElectronStream {
        emissionCurrent = emissionCurrentSetpoint;
        electronEnergy = electronEnergy;
      }
    }
  }

  part def GridIonizationRegion {
    port gasInput : VacuumPort;
    port electronInput : ElectronEmissionPort;
    port ionOutput : IonCollectionPort;

    attribute gridBiasVoltage : ElectricPotential = 180.0 [V];
    attribute ionizationVolume : Real;
    attribute sensitivity : SensitivityValue = 1.0e-4 [A / Pa];

    perform action ionization : IonizeGas {
      in gas = gasInput.sampledGas;
      in electrons = electronInput.electrons;
      out ions = ionOutput.ions;
    }
  }

  part def IonCollector {
    port ionInput : IonCollectionPort;

    attribute collectorBiasVoltage : ElectricPotential = -30.0 [V];
    attribute measuredIonCurrent : ElectricCurrent;
    attribute minimumDetectableCurrent : ElectricCurrent = 1.0e-13 [A];
    attribute leakageCurrent : ElectricCurrent = 2.0e-14 [A];

    perform action collectCurrent : CollectIonCurrent {
      in ions = ionInput.ions;
      out measuredIonCurrent = measuredIonCurrent;
    }
  }

  part def Electrometer {
    attribute inputCurrent : ElectricCurrent;
    attribute zeroOffset : ElectricCurrent = 0.0 [A];
    attribute filteredCurrent : ElectricCurrent;
    attribute integrationTime : TimeValue = 0.100 [s];

    perform action filterIonCurrent {
      in attribute rawCurrent : ElectricCurrent;
      out attribute filtered : ElectricCurrent;
    }
  }

  part def PressureProcessor {
    attribute sensitivityFactor : SensitivityValue = 1.0e-4 [A / Pa];
    attribute emissionCurrent : EmissionCurrentValue = 1.0 [mA];
    attribute calculatedPressure : PressureValue;
    attribute validRangeLow : PressureValue = 1.0e-7 [Pa];
    attribute validRangeHigh : PressureValue = 1.0e1 [Pa];

    perform action calculate : CalculatePressure {
      in ionCurrent = calculatedPressure;
      in emissionCurrent = emissionCurrent;
      in sensitivity = sensitivityFactor;
    }
  }

  part def DegasAssembly {
    attribute maximumDegasPower : DegasPowerValue = 30.0 [W];
    attribute degasDuration : TimeValue = 300.0 [s];
    attribute active : Boolean = false;
  }

  part def GaugeController {
    port commandPort : CommandInputPort;
    port measurementPort : MeasurementOutputPort;

    attribute filamentCutoffPressure : PressureValue = 1.0e1 [Pa];
    attribute warmupTime : TimeValue = 30.0 [s];
    attribute status : GaugeStatus;
    attribute currentState : GaugeOperationalState;

    perform state machine behavior : GaugeOperationalState;
  }

  part def HighVoltageSupply {
    port powerInput : PowerInputPort;

    attribute gridSupplyVoltage : ElectricPotential = 180.0 [V];
    attribute collectorSupplyVoltage : ElectricPotential = -30.0 [V];
    attribute electronAccelerationVoltage : ElectricPotential = 70.0 [V];
    attribute ready : Boolean;
  }

  part def VacuumEnvelope {
    port chamberInterface : VacuumPort;

    attribute material : String = "stainless steel";
    attribute internalTemperature : TemperatureValue = 300.0 [K];
    attribute basePressureCompatibility : PressureValue = 1.0e-8 [Pa];
  }

  part def IonizationGauge {
    port vacuumInterface : VacuumPort;
    port commandInput : CommandInputPort;
    port measurementOutput : MeasurementOutputPort;
    port powerInput : PowerInputPort;

    part envelope : VacuumEnvelope;
    part filament : FilamentAssembly;
    part ionizationRegion : GridIonizationRegion;
    part collector : IonCollector;
    part electrometer : Electrometer;
    part processor : PressureProcessor;
    part controller : GaugeController;
    part highVoltageSupply : HighVoltageSupply;
    part degasAssembly : DegasAssembly;

    attribute reportedPressure : PressureValue;
    attribute primaryFunction : String =
      "Ionize residual gas, collect resulting ion current, and report vacuum pressure.";

    connect vacuumInterface to envelope.chamberInterface;
    connect envelope.chamberInterface to ionizationRegion.gasInput;
    connect filament.electronOutput to ionizationRegion.electronInput;
    connect ionizationRegion.ionOutput to collector.ionInput;
    connect commandInput to controller.commandPort;
    connect controller.measurementPort to measurementOutput;
    connect powerInput to highVoltageSupply.powerInput;

    perform action pressureMeasurement : MeasureVacuumPressure {
      in gas = vacuumInterface.sampledGas;
      out measurement = measurementOutput.measurement;
    }

    satisfy PrimaryFunctionRequirement;
    satisfy DegasRequirement;
  }

  part def VacuumChamber {
    port gaugePort : VacuumPort;

    attribute chamberPressure : PressureValue;
    attribute gasTemperature : TemperatureValue = 300.0 [K];
    attribute dominantGasSpecies : String = "nitrogen";

    item sample : NeutralGasSample {
      estimatedPressure = chamberPressure;
      temperature = gasTemperature;
      dominantSpecies = dominantGasSpecies;
    }
  }

  part def IonizationGaugeSystem {
    part vacuumChamber : VacuumChamber;
    part gauge : IonizationGauge;

    port externalCommand : CommandInputPort;
    port externalMeasurement : MeasurementOutputPort;
    port facilityPower : PowerInputPort;

    attribute reportedPressure : PressureValue;
    attribute measurementUpdatePeriod : TimeValue = 0.250 [s];

    connect vacuumChamber.gaugePort to gauge.vacuumInterface;
    connect externalCommand to gauge.commandInput;
    connect gauge.measurementOutput to externalMeasurement;
    connect facilityPower to gauge.powerInput;

    perform action systemFunction : MeasureVacuumPressure {
      in gas = vacuumChamber.sample;
      out measurement = externalMeasurement.measurement;
    }

    satisfy PrimaryFunctionRequirement;
    satisfy FilamentProtectionRequirement;
  }

}

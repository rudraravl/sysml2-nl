package SuctionSystemSpecification {

  private import ScalarValues::*;
  private import SI::*;

  attribute def Pressure {
    :>> value : Real;
    unit : String = "Pa";
  }

  attribute def NegativePressure {
    :>> value : Real;
    unit : String = "Pa below ambient";
  }

  attribute def VolumetricFlowRate {
    :>> value : Real;
    unit : String = "L/s";
  }

  attribute def Power {
    :>> value : Real;
    unit : String = "W";
  }

  attribute def Mass {
    :>> value : Real;
    unit : String = "kg";
  }

  attribute def TimeDuration {
    :>> value : Real;
    unit : String = "s";
  }

  attribute def Efficiency {
    :>> value : Real;
    unit : String = "percent";
  }

  item def AmbientAir {
    attribute pressure : Pressure;
    attribute temperature : Real;
  }

  item def SuctionAirStream {
    attribute staticNegativePressure : NegativePressure;
    attribute flowRate : VolumetricFlowRate;
    attribute entrainedParticleMassRate : Real;
  }

  item def CollectedMaterial {
    attribute mass : Mass;
    attribute particleDiameter : Real;
    attribute moistureFraction : Real;
  }

  item def ElectricalEnergy {
    attribute voltage : Real;
    attribute current : Real;
    attribute power : Power;
  }

  port def AirIntakePort {
    in item ambientAir : AmbientAir;
    out item suctionStream : SuctionAirStream;
  }

  port def AirExhaustPort {
    out item filteredAir : AmbientAir;
  }

  port def MaterialCollectionPort {
    in item collectedMaterial : CollectedMaterial;
  }

  port def ElectricalPowerPort {
    in item supply : ElectricalEnergy;
  }

  port def ControlPort {
    in attribute startCommand : Boolean;
    in attribute stopCommand : Boolean;
    in attribute targetSuction : NegativePressure;
    out attribute operating : Boolean;
    out attribute faultActive : Boolean;
  }

  part def SuctionNozzle {
    attribute inletArea : Real = 0.0035;
    attribute standoffDistance : Real = 0.012;
    attribute pickupWidth : Real = 0.18;

    port mouth : AirIntakePort;
    port materialInlet : MaterialCollectionPort;
  }

  part def SuctionDuct {
    attribute length : Real = 1.2;
    attribute insideDiameter : Real = 0.032;
    attribute pressureLossAtNominalFlow : Pressure = 850.0;
    attribute leakRateAtNominalPressure : VolumetricFlowRate = 0.25;

    port inlet : AirIntakePort;
    port outlet : AirIntakePort;
  }

  part def ImpellerBlower {
    attribute ratedSpeed : Real = 42000.0;
    attribute ratedPower : Power = 650.0;
    attribute maximumNegativePressure : NegativePressure = 22000.0;
    attribute nominalFlowRate : VolumetricFlowRate = 32.0;
    attribute mechanicalEfficiency : Efficiency = 72.0;

    port airIn : AirIntakePort;
    port airOut : AirExhaustPort;
    port powerIn : ElectricalPowerPort;
  }

  part def Separator {
    attribute separationEfficiencyFor100MicronParticles : Efficiency = 96.0;
    attribute maximumStoredMass : Mass = 2.0;
    attribute currentStoredMass : Mass = 0.0;

    port inlet : AirIntakePort;
    port cleanAirOutlet : AirIntakePort;
    port materialOutlet : MaterialCollectionPort;
  }

  part def Filter {
    attribute filtrationEfficiencyFor1MicronParticles : Efficiency = 99.5;
    attribute cleanPressureDrop : Pressure = 450.0;
    attribute cloggedPressureDropLimit : Pressure = 3500.0;
    attribute accumulatedDustMass : Mass = 0.0;

    port inlet : AirIntakePort;
    port outlet : AirExhaustPort;
  }

  part def SuctionController {
    attribute commandedNegativePressure : NegativePressure = 12000.0;
    attribute measuredNegativePressure : NegativePressure = 0.0;
    attribute measuredFlowRate : VolumetricFlowRate = 0.0;
    attribute motorDutyCycle : Real = 0.0;
    attribute faultDetected : Boolean = false;

    port controls : ControlPort;
  }

  part def PressureSensor {
    attribute measuredPressure : NegativePressure = 0.0;
    attribute responseTime : TimeDuration = 0.05;
  }

  part def FlowSensor {
    attribute measuredFlow : VolumetricFlowRate = 0.0;
    attribute responseTime : TimeDuration = 0.10;
  }

  part def SuctionSystem {
    attribute ambientPressure : Pressure = 101325.0;
    attribute nominalNegativePressure : NegativePressure = 12000.0;
    attribute minimumEffectiveNegativePressure : NegativePressure = 7000.0;
    attribute nominalAirFlow : VolumetricFlowRate = 28.0;
    attribute maximumInputPower : Power = 750.0;
    attribute continuousOperatingTime : TimeDuration = 1800.0;

    port suctionInterface : AirIntakePort;
    port exhaustInterface : AirExhaustPort;
    port electricalInterface : ElectricalPowerPort;
    port commandInterface : ControlPort;

    part nozzle : SuctionNozzle;
    part duct : SuctionDuct;
    part blower : ImpellerBlower;
    part separator : Separator;
    part filter : Filter;
    part controller : SuctionController;
    part pressureSensor : PressureSensor;
    part flowSensor : FlowSensor;

    connect suctionInterface to nozzle.mouth;
    connect nozzle.mouth to duct.inlet;
    connect duct.outlet to separator.inlet;
    connect separator.cleanAirOutlet to blower.airIn;
    connect blower.airOut to filter.inlet;
    connect filter.outlet to exhaustInterface;
    connect electricalInterface to blower.powerIn;
    connect commandInterface to controller.controls;

    perform action provideSuction : ProvideSuction;
    exhibit state behavior operatingLifeCycle : SuctionOperatingStateMachine;
  }

  action def ProvideSuction {
    in attribute start : Boolean;
    in attribute targetNegativePressure : NegativePressure;
    in item ambientAir : AmbientAir;
    in item looseMaterial : CollectedMaterial;
    out item suctionStream : SuctionAirStream;
    out item storedMaterial : CollectedMaterial;
    out item exhaustAir : AmbientAir;

    action energizeBlower {
      in attribute requestedPressure : NegativePressure;
      out attribute shaftPower : Power;
    }

    action createLowPressureRegion {
      in attribute blowerPower : Power;
      out attribute generatedNegativePressure : NegativePressure;
    }

    action entrainMaterial {
      in item air : AmbientAir;
      in item material : CollectedMaterial;
      out item mixedStream : SuctionAirStream;
    }

    action separateMaterial {
      in item mixedStream : SuctionAirStream;
      out item retainedMaterial : CollectedMaterial;
      out item cleanedStream : SuctionAirStream;
    }

    action filterExhaust {
      in item cleanedStream : SuctionAirStream;
      out item cleanAir : AmbientAir;
    }

    flow start to energizeBlower;
    flow targetNegativePressure to energizeBlower.requestedPressure;
    flow energizeBlower.shaftPower to createLowPressureRegion.blowerPower;
    flow ambientAir to entrainMaterial.air;
    flow looseMaterial to entrainMaterial.material;
    flow entrainMaterial.mixedStream to separateMaterial.mixedStream;
    flow separateMaterial.retainedMaterial to storedMaterial;
    flow separateMaterial.cleanedStream to filterExhaust.cleanedStream;
    flow filterExhaust.cleanAir to exhaustAir;
    flow separateMaterial.cleanedStream to suctionStream;
  }

  state def SuctionOperatingStateMachine {
    state Off;
    state Starting;
    state Running;
    state ReducedSuction;
    state Clogged;
    state Fault;
    state Shutdown;

    transition initial then Off;

    transition Off_to_Starting
      first Off
      accept commandInterface.startCommand
      then Starting;

    transition Starting_to_Running
      first Starting
      if pressureSensor.measuredPressure >= minimumEffectiveNegativePressure
      then Running;

    transition Starting_to_Fault
      first Starting
      if pressureSensor.measuredPressure < minimumEffectiveNegativePressure
      after 5.0
      then Fault;

    transition Running_to_ReducedSuction
      first Running
      if flowSensor.measuredFlow < 0.70 * nominalAirFlow
      then ReducedSuction;

    transition ReducedSuction_to_Running
      first ReducedSuction
      if flowSensor.measuredFlow >= 0.85 * nominalAirFlow
      then Running;

    transition ReducedSuction_to_Clogged
      first ReducedSuction
      if filter.accumulatedDustMass > 0.75 or filter.cleanPressureDrop >= filter.cloggedPressureDropLimit
      then Clogged;

    transition Clogged_to_Shutdown
      first Clogged
      accept commandInterface.stopCommand
      then Shutdown;

    transition Running_to_Shutdown
      first Running
      accept commandInterface.stopCommand
      then Shutdown;

    transition Shutdown_to_Off
      first Shutdown
      after 2.0
      then Off;

    transition Running_to_Fault
      first Running
      if controller.faultDetected
      then Fault;

    transition Fault_to_Off
      first Fault
      accept commandInterface.stopCommand
      then Off;
  }

  requirement def PrimaryFunctionRequirement {
    subject system : SuctionSystem;

    doc /* The suction system shall create and maintain a controlled low-pressure region at its intake so that surrounding air accelerates into the nozzle, entrains loose material, transports it through the duct, separates retained material, and exhausts filtered air. */

    require constraint {
      system.pressureSensor.measuredPressure >= system.minimumEffectiveNegativePressure
    }

    require constraint {
      system.flowSensor.measuredFlow >= 0.70 * system.nominalAirFlow
    }
  }

  requirement def SuctionPressureRequirement {
    subject system : SuctionSystem;

    doc /* During normal running operation, the system shall regulate intake negative pressure to the commanded target without exceeding blower capability. */

    require constraint {
      system.controller.commandedNegativePressure <= system.blower.maximumNegativePressure
    }

    require constraint {
      system.controller.measuredNegativePressure >= 0.90 * system.controller.commandedNegativePressure
    }
  }

  requirement def MaterialSeparationRequirement {
    subject system : SuctionSystem;

    doc /* The system shall retain collected material while allowing cleaned air to continue to the blower and exhaust path. */

    require constraint {
      system.separator.separationEfficiencyFor100MicronParticles >= 95.0
    }

    require constraint {
      system.separator.currentStoredMass <= system.separator.maximumStoredMass
    }
  }

  requirement def FiltrationRequirement {
    subject system : SuctionSystem;

    doc /* The exhaust path shall filter fine particles before air leaves the system. */

    require constraint {
      system.filter.filtrationEfficiencyFor1MicronParticles >= 99.0
    }

    require constraint {
      system.filter.cleanPressureDrop < system.filter.cloggedPressureDropLimit
    }
  }

  requirement def PowerRequirement {
    subject system : SuctionSystem;

    doc /* The suction system shall perform its primary suction function within the available electrical power limit. */

    require constraint {
      system.blower.ratedPower <= system.maximumInputPower
    }
  }

  requirement def SafetyShutdownRequirement {
    subject system : SuctionSystem;

    doc /* The controller shall transition the system out of running operation when a persistent clog or fault is detected. */

    require constraint {
      system.controller.faultDetected implies system.commandInterface.faultActive
    }
  }

}

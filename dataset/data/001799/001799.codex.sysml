package IrrigationSystemModel {

    import ScalarValues::*;
    import SI::*;

    attribute def Percentage : Real {
        doc /* Fractional percentage from 0 to 100. */
    }

    attribute def SoilMoisturePercent : Percentage {
        doc /* Volumetric soil moisture expressed as a percentage. */
    }

    attribute def WaterFlowRate : Real {
        unit = L / min;
    }

    attribute def WaterVolume : Real {
        unit = L;
    }

    attribute def Pressure : Real {
        unit = kPa;
    }

    attribute def Duration : Real {
        unit = s;
    }

    attribute def Area : Real {
        unit = m^2;
    }

    attribute def ElectricPower : Real {
        unit = W;
    }

    attribute def Voltage : Real {
        unit = V;
    }

    enum def IrrigationMode {
        enum manual;
        enum scheduled;
        enum automatic;
        enum maintenance;
    }

    enum def ValvePosition {
        enum open;
        enum closed;
        enum modulating;
    }

    enum def PumpStatus {
        enum off;
        enum starting;
        enum running;
        enum faulted;
    }

    enum def AlertSeverity {
        enum advisory;
        enum warning;
        enum critical;
    }

    item def Water {
        attribute volume : WaterVolume;
        attribute pressure : Pressure;
        attribute flowRate : WaterFlowRate;
    }

    item def ElectricalEnergy {
        attribute voltage : Voltage;
        attribute power : ElectricPower;
    }

    item def MoistureReading {
        attribute measuredMoisture : SoilMoisturePercent;
        attribute sensorHealth : Percentage;
        attribute sampleAge : Duration;
    }

    item def WeatherForecast {
        attribute expectedRainfall : WaterVolume;
        attribute forecastHorizon : Duration;
        attribute evapotranspirationEstimate : WaterVolume;
    }

    item def IrrigationCommand {
        attribute targetZoneId : Integer;
        attribute requestedDuration : Duration;
        attribute requestedFlowRate : WaterFlowRate;
        attribute mode : IrrigationMode;
    }

    item def ValveCommand {
        attribute targetPosition : ValvePosition;
        attribute openingPercent : Percentage;
    }

    item def PumpCommand {
        attribute enable : Boolean;
        attribute targetPressure : Pressure;
    }

    item def SystemAlert {
        attribute severity : AlertSeverity;
        attribute alertCode : String;
        attribute active : Boolean;
    }

    port def WaterInletPort {
        in item suppliedWater : Water;
    }

    port def WaterOutletPort {
        out item deliveredWater : Water;
    }

    port def PowerInputPort {
        in item inputEnergy : ElectricalEnergy;
    }

    port def SensorOutputPort {
        out item reading : MoistureReading;
    }

    port def ForecastInputPort {
        in item forecast : WeatherForecast;
    }

    port def CommandInputPort {
        in item command : IrrigationCommand;
    }

    port def ValveControlPort {
        out item command : ValveCommand;
    }

    port def PumpControlPort {
        out item command : PumpCommand;
    }

    port def AlertOutputPort {
        out item alert : SystemAlert;
    }

    part def SoilMoistureSensor {
        attribute sensorId : Integer;
        attribute measurementRangeMin : SoilMoisturePercent = 0.0;
        attribute measurementRangeMax : SoilMoisturePercent = 100.0;
        attribute accuracy : Percentage = 3.0;
        attribute samplePeriod : Duration = 60.0;
        attribute currentReading : SoilMoisturePercent;

        port sensorOutput : SensorOutputPort;

        action senseSoilMoisture {
            out item reading : MoistureReading;
        }
    }

    part def WeatherServiceInterface {
        attribute updatePeriod : Duration = 3600.0;
        attribute forecastWindow : Duration = 86400.0;

        port forecastInput : ForecastInputPort;

        action receiveForecast {
            in item forecast : WeatherForecast;
        }
    }

    part def IrrigationController {
        attribute activeMode : IrrigationMode = IrrigationMode::automatic;
        attribute targetMoisture : SoilMoisturePercent = 35.0;
        attribute lowerMoistureThreshold : SoilMoisturePercent = 25.0;
        attribute upperMoistureThreshold : SoilMoisturePercent = 42.0;
        attribute rainSkipThreshold : WaterVolume = 8.0;
        attribute maximumZoneRuntime : Duration = 2700.0;
        attribute controlCyclePeriod : Duration = 30.0;

        port commandInput : CommandInputPort;
        port forecastInput : ForecastInputPort;
        port valveControl : ValveControlPort;
        port pumpControl : PumpControlPort;
        port alertOutput : AlertOutputPort;

        action evaluateIrrigationNeed {
            in item moisture : MoistureReading;
            in item forecast : WeatherForecast;
            out item command : IrrigationCommand;
        }

        action commandValve {
            in item irrigationCommand : IrrigationCommand;
            out item valveCommand : ValveCommand;
        }

        action commandPump {
            in item irrigationCommand : IrrigationCommand;
            out item pumpCommand : PumpCommand;
        }

        state controllerState {
            entry action initializeControl {
                then idle;
            }

            state idle;
            state monitoring;
            state deciding;
            state irrigating;
            state rainDelay;
            state faultResponse;
            state manualOverride;
            state maintenanceMode;

            transition idle_to_monitoring
                first idle
                then monitoring;

            transition monitoring_to_deciding
                first monitoring
                then deciding;

            transition deciding_to_irrigating
                first deciding
                then irrigating
                if lowerMoistureThreshold > currentZoneAverageMoisture;

            transition deciding_to_rainDelay
                first deciding
                then rainDelay
                if predictedRainfall >= rainSkipThreshold;

            transition deciding_to_monitoring
                first deciding
                then monitoring
                if currentZoneAverageMoisture >= lowerMoistureThreshold;

            transition irrigating_to_monitoring
                first irrigating
                then monitoring
                if currentZoneAverageMoisture >= upperMoistureThreshold;

            transition irrigating_to_faultResponse
                first irrigating
                then faultResponse
                if detectedLeak or pumpFault or lowSupplyPressure;

            transition monitoring_to_manualOverride
                first monitoring
                then manualOverride
                if activeMode == IrrigationMode::manual;

            transition manualOverride_to_monitoring
                first manualOverride
                then monitoring
                if activeMode != IrrigationMode::manual;

            transition monitoring_to_maintenanceMode
                first monitoring
                then maintenanceMode
                if activeMode == IrrigationMode::maintenance;

            transition faultResponse_to_monitoring
                first faultResponse
                then monitoring
                if faultCleared;
        }

        attribute currentZoneAverageMoisture : SoilMoisturePercent;
        attribute predictedRainfall : WaterVolume;
        attribute detectedLeak : Boolean = false;
        attribute pumpFault : Boolean = false;
        attribute lowSupplyPressure : Boolean = false;
        attribute faultCleared : Boolean = true;
    }

    part def PumpAssembly {
        attribute status : PumpStatus = PumpStatus::off;
        attribute ratedFlowRate : WaterFlowRate = 75.0;
        attribute ratedPressure : Pressure = 350.0;
        attribute powerDraw : ElectricPower = 1200.0;
        attribute minimumInletPressure : Pressure = 120.0;

        port waterIn : WaterInletPort;
        port waterOut : WaterOutletPort;
        port powerIn : PowerInputPort;
        port pumpControl : PumpControlPort;

        action pressurizeWater {
            in item inletWater : Water;
            in item pumpCommand : PumpCommand;
            out item outletWater : Water;
        }

        state pumpState {
            state off;
            state starting;
            state running;
            state faulted;

            transition off_to_starting
                first off
                then starting
                if commandedEnable;

            transition starting_to_running
                first starting
                then running
                if outletPressure >= targetPressure;

            transition running_to_off
                first running
                then off
                if not commandedEnable;

            transition running_to_faulted
                first running
                then faulted
                if inletPressure < minimumInletPressure;

            transition faulted_to_off
                first faulted
                then off
                if resetCommanded;
        }

        attribute commandedEnable : Boolean = false;
        attribute resetCommanded : Boolean = false;
        attribute inletPressure : Pressure;
        attribute outletPressure : Pressure;
        attribute targetPressure : Pressure;
    }

    part def ZoneValve {
        attribute valveId : Integer;
        attribute position : ValvePosition = ValvePosition::closed;
        attribute maximumFlowRate : WaterFlowRate = 25.0;
        attribute leakageFlowWhenClosed : WaterFlowRate = 0.05;

        port valveControl : ValveControlPort;
        port waterIn : WaterInletPort;
        port waterOut : WaterOutletPort;

        action regulateFlow {
            in item valveCommand : ValveCommand;
            in item inletWater : Water;
            out item outletWater : Water;
        }

        state valveState {
            state closed;
            state opening;
            state open;
            state modulating;
            state closing;

            transition closed_to_opening
                first closed
                then opening
                if commandedPosition == ValvePosition::open;

            transition opening_to_open
                first opening
                then open
                if openingPercent >= 100.0;

            transition open_to_modulating
                first open
                then modulating
                if commandedPosition == ValvePosition::modulating;

            transition modulating_to_closing
                first modulating
                then closing
                if commandedPosition == ValvePosition::closed;

            transition open_to_closing
                first open
                then closing
                if commandedPosition == ValvePosition::closed;

            transition closing_to_closed
                first closing
                then closed
                if openingPercent <= 0.0;
        }

        attribute commandedPosition : ValvePosition;
        attribute openingPercent : Percentage;
    }

    part def DripEmitterLine {
        attribute emitterCount : Integer;
        attribute emitterFlowRate : WaterFlowRate = 2.0;
        attribute distributionUniformity : Percentage = 90.0;
        attribute irrigatedArea : Area;

        port waterIn : WaterInletPort;
        port waterOut : WaterOutletPort;

        action distributeWater {
            in item inletWater : Water;
            out item deliveredWater : Water;
        }
    }

    part def IrrigationZone {
        attribute zoneId : Integer;
        attribute cropType : String;
        attribute area : Area;
        attribute targetRootZoneMoisture : SoilMoisturePercent;
        attribute currentAverageMoisture : SoilMoisturePercent;
        attribute dailyWaterBudget : WaterVolume;

        part valve : ZoneValve;
        part emitterLine : DripEmitterLine;
        part moistureSensor[2] : SoilMoistureSensor;

        port waterIn : WaterInletPort;
        port waterOut : WaterOutletPort;
        port valveControl : ValveControlPort;
        port sensorOutput : SensorOutputPort;

        connection zoneSupply
            connect waterIn to valve.waterIn;

        connection valveToEmitter
            connect valve.waterOut to emitterLine.waterIn;

        connection zoneDelivery
            connect emitterLine.waterOut to waterOut;

        connection valveCommandPath
            connect valveControl to valve.valveControl;
    }

    part def WaterSupply {
        attribute storageCapacity : WaterVolume = 5000.0;
        attribute availableVolume : WaterVolume = 4200.0;
        attribute nominalSupplyPressure : Pressure = 180.0;
        attribute refillRate : WaterFlowRate = 30.0;

        port waterOut : WaterOutletPort;

        action provideWater {
            out item suppliedWater : Water;
        }
    }

    part def PowerSubsystem {
        attribute nominalVoltage : Voltage = 240.0;
        attribute maximumPower : ElectricPower = 2500.0;
        attribute backupRuntime : Duration = 7200.0;

        port powerOut : PowerInputPort;

        action supplyPower {
            out item energy : ElectricalEnergy;
        }
    }

    part def UserInterface {
        attribute selectedMode : IrrigationMode = IrrigationMode::automatic;
        attribute manualZoneSelection : Integer = 1;
        attribute manualRuntime : Duration = 900.0;

        port commandOutput : CommandInputPort;
        port alertInput : AlertOutputPort;

        action requestManualIrrigation {
            out item command : IrrigationCommand;
        }

        action displayAlert {
            in item alert : SystemAlert;
        }
    }

    part def IrrigationSystem {
        doc /* The irrigation system monitors soil moisture, weather forecast, water supply, and user commands to deliver controlled water to plant zones. Its primary high-level function is to maintain soil moisture within target limits while minimizing wasted water and protecting equipment from unsafe operating conditions. */

        attribute installedArea : Area = 1200.0;
        attribute totalDailyWaterLimit : WaterVolume = 900.0;
        attribute nominalOperatingPressure : Pressure = 300.0;
        attribute activeMode : IrrigationMode = IrrigationMode::automatic;

        part supply : WaterSupply;
        part power : PowerSubsystem;
        part pump : PumpAssembly;
        part controller : IrrigationController;
        part weatherInterface : WeatherServiceInterface;
        part userInterface : UserInterface;

        part vegetableZone : IrrigationZone {
            attribute zoneId = 1;
            attribute cropType = "vegetables";
            attribute area = 350.0;
            attribute targetRootZoneMoisture = 38.0;
            attribute dailyWaterBudget = 260.0;
        }

        part orchardZone : IrrigationZone {
            attribute zoneId = 2;
            attribute cropType = "fruit trees";
            attribute area = 500.0;
            attribute targetRootZoneMoisture = 32.0;
            attribute dailyWaterBudget = 390.0;
        }

        part lawnZone : IrrigationZone {
            attribute zoneId = 3;
            attribute cropType = "turf grass";
            attribute area = 350.0;
            attribute targetRootZoneMoisture = 30.0;
            attribute dailyWaterBudget = 250.0;
        }

        port waterSupplyIn : WaterInletPort;
        port alertOut : AlertOutputPort;
        port commandIn : CommandInputPort;
        port forecastIn : ForecastInputPort;

        connection externalWaterToSupply
            connect waterSupplyIn to supply.waterOut;

        connection supplyToPump
            connect supply.waterOut to pump.waterIn;

        connection pumpToVegetableZone
            connect pump.waterOut to vegetableZone.waterIn;

        connection pumpToOrchardZone
            connect pump.waterOut to orchardZone.waterIn;

        connection pumpToLawnZone
            connect pump.waterOut to lawnZone.waterIn;

        connection powerToPump
            connect power.powerOut to pump.powerIn;

        connection controllerToPump
            connect controller.pumpControl to pump.pumpControl;

        connection controllerToVegetableValve
            connect controller.valveControl to vegetableZone.valveControl;

        connection controllerToOrchardValve
            connect controller.valveControl to orchardZone.valveControl;

        connection controllerToLawnValve
            connect controller.valveControl to lawnZone.valveControl;

        connection userCommandToController
            connect userInterface.commandOutput to controller.commandInput;

        connection externalCommandToController
            connect commandIn to controller.commandInput;

        connection forecastToWeatherInterface
            connect forecastIn to weatherInterface.forecastInput;

        connection weatherToController
            connect weatherInterface.forecastInput to controller.forecastInput;

        connection controllerAlertToSystem
            connect controller.alertOutput to alertOut;

        connection controllerAlertToUser
            connect controller.alertOutput to userInterface.alertInput;

        action performPrimaryIrrigationFunction {
            in item forecast : WeatherForecast;
            in item userCommand : IrrigationCommand;
            out item deliveredWater : Water;
            out item alert : SystemAlert;

            first receiveInputs;
            then assessZoneMoisture;
            then decideWatering;
            then pressurizeSupply;
            then openSelectedValves;
            then distributeWater;
            then stopWhenTargetReached;
        }

        action receiveInputs {
            in item forecast : WeatherForecast;
            in item userCommand : IrrigationCommand;
        }

        action assessZoneMoisture {
            out attribute vegetableMoisture : SoilMoisturePercent;
            out attribute orchardMoisture : SoilMoisturePercent;
            out attribute lawnMoisture : SoilMoisturePercent;
        }

        action decideWatering {
            in attribute vegetableMoisture : SoilMoisturePercent;
            in attribute orchardMoisture : SoilMoisturePercent;
            in attribute lawnMoisture : SoilMoisturePercent;
            out item command : IrrigationCommand;
        }

        action pressurizeSupply {
            in item command : PumpCommand;
            out item pressurizedWater : Water;
        }

        action openSelectedValves {
            in item command : ValveCommand;
        }

        action distributeWater {
            in item pressurizedWater : Water;
            out item deliveredWater : Water;
        }

        action stopWhenTargetReached {
            out item shutdownCommand : IrrigationCommand;
        }
    }

    requirement def MaintainSoilMoisture {
        doc /* The system shall maintain each irrigation zone within its configured soil moisture band during automatic operation. */
        attribute lowerLimit : SoilMoisturePercent;
        attribute upperLimit : SoilMoisturePercent;
    }

    requirement def MinimizeWaterWaste {
        doc /* The system shall avoid irrigation when forecast rainfall is sufficient to meet near-term plant water demand. */
        attribute rainSkipThreshold : WaterVolume;
        attribute forecastHorizon : Duration;
    }

    requirement def ProtectPump {
        doc /* The system shall stop the pump and issue a critical alert when inlet pressure is below the safe operating limit. */
        attribute minimumSafePressure : Pressure;
        attribute shutdownTime : Duration;
    }

    requirement def LimitDailyWaterUse {
        doc /* The system shall prevent total daily water delivery from exceeding the configured daily water limit. */
        attribute dailyLimit : WaterVolume;
    }

    requirement def ManualOverride {
        doc /* The system shall allow an operator to manually start or stop irrigation for a selected zone while preserving equipment safety limits. */
        attribute maximumManualRuntime : Duration;
    }

    requirement maintainVegetableMoisture : MaintainSoilMoisture {
        attribute lowerLimit = 28.0;
        attribute upperLimit = 42.0;
    }

    requirement maintainOrchardMoisture : MaintainSoilMoisture {
        attribute lowerLimit = 24.0;
        attribute upperLimit = 38.0;
    }

    requirement maintainLawnMoisture : MaintainSoilMoisture {
        attribute lowerLimit = 22.0;
        attribute upperLimit = 35.0;
    }

    requirement skipForRain : MinimizeWaterWaste {
        attribute rainSkipThreshold = 8.0;
        attribute forecastHorizon = 86400.0;
    }

    requirement pumpDryRunProtection : ProtectPump {
        attribute minimumSafePressure = 120.0;
        attribute shutdownTime = 5.0;
    }

    requirement dailyUseConstraint : LimitDailyWaterUse {
        attribute dailyLimit = 900.0;
    }

    requirement manualControlConstraint : ManualOverride {
        attribute maximumManualRuntime = 1800.0;
    }

    satisfy maintainVegetableMoisture by IrrigationSystem::vegetableZone;
    satisfy maintainOrchardMoisture by IrrigationSystem::orchardZone;
    satisfy maintainLawnMoisture by IrrigationSystem::lawnZone;
    satisfy skipForRain by IrrigationSystem::controller;
    satisfy pumpDryRunProtection by IrrigationSystem::pump;
    satisfy dailyUseConstraint by IrrigationSystem;
    satisfy manualControlConstraint by IrrigationSystem::userInterface;

    constraint def MoistureWithinBand {
        in attribute moisture : SoilMoisturePercent;
        in attribute lower : SoilMoisturePercent;
        in attribute upper : SoilMoisturePercent;
        moisture >= lower and moisture <= upper
    }

    constraint def DailyWaterBudgetNotExceeded {
        in attribute deliveredToday : WaterVolume;
        in attribute dailyLimit : WaterVolume;
        deliveredToday <= dailyLimit
    }

    constraint def PumpPressureSafe {
        in attribute inletPressure : Pressure;
        in attribute minimumSafePressure : Pressure;
        inletPressure >= minimumSafePressure
    }

    allocation def ControlAllocation {
        end controllerFunction : IrrigationSystem::performPrimaryIrrigationFunction;
        end physicalController : IrrigationSystem::controller;
    }

    allocation primaryFunctionToController : ControlAllocation {
        end controllerFunction = IrrigationSystem::performPrimaryIrrigationFunction;
        end physicalController = IrrigationSystem::controller;
    }
}

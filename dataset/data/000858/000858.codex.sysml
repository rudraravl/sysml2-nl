package ChainPumpSubsystemModel {

    import ScalarValues::*;
    import ISQ::*;
    import SI::*;

    attribute def FlowRate {
        attribute value : Real;
        attribute unit : String = "L/min";
    }

    attribute def Pressure {
        attribute value : Real;
        attribute unit : String = "kPa";
    }

    attribute def RotationalSpeed {
        attribute value : Real;
        attribute unit : String = "rpm";
    }

    attribute def Torque {
        attribute value : Real;
        attribute unit : String = "N*m";
    }

    attribute def Power {
        attribute value : Real;
        attribute unit : String = "W";
    }

    attribute def Temperature {
        attribute value : Real;
        attribute unit : String = "degC";
    }

    attribute def Length {
        attribute value : Real;
        attribute unit : String = "mm";
    }

    attribute def Efficiency {
        attribute value : Real;
        attribute unit : String = "percent";
    }

    item def WorkingFluid {
        attribute density : Real = 998.0;
        attribute dynamicViscosity : Real = 0.001;
        attribute temperature : Temperature;
        attribute solidsContentPercent : Real;
    }

    item def ElectricalEnergy {
        attribute voltage : Real;
        attribute current : Real;
        attribute frequency : Real;
    }

    item def ControlSignal {
        attribute command : String;
        attribute setpointSpeed : RotationalSpeed;
        attribute enable : Boolean;
    }

    item def SensorSignal {
        attribute measuredFlow : FlowRate;
        attribute measuredPressure : Pressure;
        attribute measuredTemperature : Temperature;
        attribute faultActive : Boolean;
    }

    port def FluidInletPort {
        in item fluid : WorkingFluid;
        attribute staticPressure : Pressure;
    }

    port def FluidOutletPort {
        out item fluid : WorkingFluid;
        attribute dischargePressure : Pressure;
        attribute deliveredFlow : FlowRate;
    }

    port def PowerInputPort {
        in item energy : ElectricalEnergy;
    }

    port def ControlInputPort {
        in item signal : ControlSignal;
    }

    port def TelemetryOutputPort {
        out item telemetry : SensorSignal;
    }

    port def DrainPort {
        out item leakage : WorkingFluid;
    }

    part def ChainPumpSubsystem {
        attribute requiredFlow : FlowRate = (value = 120.0; unit = "L/min");
        attribute requiredDischargePressure : Pressure = (value = 350.0; unit = "kPa");
        attribute maximumFluidTemperature : Temperature = (value = 60.0; unit = "degC");
        attribute nominalEfficiency : Efficiency = (value = 72.0; unit = "percent");

        port inlet : FluidInletPort;
        port outlet : FluidOutletPort;
        port powerInput : PowerInputPort;
        port controlInput : ControlInputPort;
        port telemetryOutput : TelemetryOutputPort;
        port drain : DrainPort;

        part frame : PumpFrame;
        part chainPump : ChainPump;
        part driveMotor : ElectricMotor;
        part gearbox : GearReducer;
        part chainGuard : GuardAssembly;
        part fluidReservoirInterface : ReservoirInterface;
        part suctionStrainer : Strainer;
        part dischargeCheckValve : CheckValve;
        part pressureReliefValve : ReliefValve;
        part controller : PumpController;
        part sensorSet : SensorSet;
        part lubricationSystem : LubricationSystem;
        part basePlate : BasePlate;

        connect inlet to suctionStrainer.inlet;
        connect suctionStrainer.outlet to chainPump.suctionPort;
        connect chainPump.dischargePort to dischargeCheckValve.inlet;
        connect dischargeCheckValve.outlet to outlet;
        connect chainPump.leakagePort to drain;
        connect powerInput to driveMotor.powerPort;
        connect controlInput to controller.commandPort;
        connect controller.motorCommandPort to driveMotor.controlPort;
        connect driveMotor.shaftPort to gearbox.inputShaft;
        connect gearbox.outputShaft to chainPump.driveShaft;
        connect sensorSet.telemetryPort to telemetryOutput;
        connect sensorSet.flowTap to outlet;
        connect sensorSet.pressureTap to outlet;
        connect sensorSet.temperatureTap to chainPump.casingPort;
        connect pressureReliefValve.inlet to chainPump.dischargePort;
        connect pressureReliefValve.outlet to fluidReservoirInterface.returnPort;
        connect lubricationSystem.lubeOutlet to chainPump.bearingLubePort;

        perform behavior operate : PumpingOperation;
    }

    part def ChainPump {
        attribute chainPitch : Length = (value = 38.1; unit = "mm");
        attribute numberOfLinks : Integer = 84;
        attribute bucketVolume : Real = 0.18;
        attribute bucketVolumeUnit : String = "L";
        attribute nominalSpeed : RotationalSpeed = (value = 90.0; unit = "rpm");
        attribute maximumSpeed : RotationalSpeed = (value = 140.0; unit = "rpm");
        attribute casingPressureRating : Pressure = (value = 600.0; unit = "kPa");

        port suctionPort : FluidInletPort;
        port dischargePort : FluidOutletPort;
        port driveShaft : ShaftPort;
        port leakagePort : DrainPort;
        port casingPort : TelemetryOutputPort;
        port bearingLubePort : LubricantPort;

        part chainLoop : ChainLoop;
        part lowerSprocket : Sprocket;
        part upperSprocket : Sprocket;
        part bucketSet : BucketSet;
        part casing : PumpCasing;
        part shaftSeal : ShaftSeal;
        part bearings : BearingSet;
        part tensioner : ChainTensioner;

        connect chainLoop.lowerEngagement to lowerSprocket.teeth;
        connect chainLoop.upperEngagement to upperSprocket.teeth;
        connect bucketSet.mounts to chainLoop.attachments;
        connect driveShaft to upperSprocket.shaft;
        connect bearings.supportedShaft to upperSprocket.shaft;
        connect tensioner.contactPad to chainLoop.slackSpan;
    }

    port def ShaftPort {
        inout attribute speed : RotationalSpeed;
        inout attribute torque : Torque;
    }

    port def LubricantPort {
        in item lubricant : WorkingFluid;
        attribute lubricantFlow : FlowRate;
    }

    port def MechanicalEngagementPort {
        inout attribute transmittedForce : Real;
    }

    part def ChainLoop {
        attribute tensileRating : Real = 22000.0;
        attribute tensileRatingUnit : String = "N";
        attribute corrosionAllowance : Length = (value = 1.5; unit = "mm");

        port lowerEngagement : MechanicalEngagementPort;
        port upperEngagement : MechanicalEngagementPort;
        port attachments : MechanicalEngagementPort;
        port slackSpan : MechanicalEngagementPort;
    }

    part def Sprocket {
        attribute toothCount : Integer = 18;
        attribute pitchDiameter : Length = (value = 218.0; unit = "mm");
        attribute material : String = "316 stainless steel";

        port teeth : MechanicalEngagementPort;
        port shaft : ShaftPort;
    }

    part def BucketSet {
        attribute bucketCount : Integer = 42;
        attribute bucketMaterial : String = "glass-filled nylon";
        attribute bucketFillFactor : Real = 0.82;

        port mounts : MechanicalEngagementPort;
    }

    part def PumpCasing {
        attribute material : String = "316 stainless steel";
        attribute accessCoverInterlocked : Boolean = true;
        attribute internalClearance : Length = (value = 4.0; unit = "mm");
    }

    part def ShaftSeal {
        attribute sealType : String = "double mechanical seal";
        attribute maximumLeakage : FlowRate = (value = 0.05; unit = "L/min");
    }

    part def BearingSet {
        attribute bearingType : String = "sealed angular contact";
        attribute designLifeHours : Real = 25000.0;

        port supportedShaft : ShaftPort;
    }

    part def ChainTensioner {
        attribute preloadForce : Real = 850.0;
        attribute preloadForceUnit : String = "N";
        attribute travel : Length = (value = 45.0; unit = "mm");

        port contactPad : MechanicalEngagementPort;
    }

    part def ElectricMotor {
        attribute ratedPower : Power = (value = 2200.0; unit = "W");
        attribute ratedSpeed : RotationalSpeed = (value = 1750.0; unit = "rpm");
        attribute protectionRating : String = "IP55";
        attribute insulationClass : String = "F";

        port powerPort : PowerInputPort;
        port controlPort : ControlInputPort;
        port shaftPort : ShaftPort;
    }

    part def GearReducer {
        attribute ratio : Real = 19.44;
        attribute serviceFactor : Real = 1.5;
        attribute efficiency : Efficiency = (value = 91.0; unit = "percent");

        port inputShaft : ShaftPort;
        port outputShaft : ShaftPort;
    }

    part def GuardAssembly {
        attribute material : String = "powder-coated steel";
        attribute removableWithToolOnly : Boolean = true;
        attribute interlockInstalled : Boolean = true;
    }

    part def PumpFrame {
        attribute material : String = "welded stainless steel";
        attribute naturalFrequency : Real = 42.0;
        attribute naturalFrequencyUnit : String = "Hz";
    }

    part def BasePlate {
        attribute flatnessTolerance : Length = (value = 0.5; unit = "mm");
        attribute anchorBoltCount : Integer = 4;
    }

    part def ReservoirInterface {
        port returnPort : FluidInletPort;
    }

    part def Strainer {
        attribute meshOpening : Length = (value = 2.0; unit = "mm");
        attribute cleanPressureDrop : Pressure = (value = 8.0; unit = "kPa");

        port inlet : FluidInletPort;
        port outlet : FluidOutletPort;
    }

    part def CheckValve {
        attribute crackingPressure : Pressure = (value = 12.0; unit = "kPa");
        attribute reverseLeakageLimit : FlowRate = (value = 0.02; unit = "L/min");

        port inlet : FluidInletPort;
        port outlet : FluidOutletPort;
    }

    part def ReliefValve {
        attribute setPressure : Pressure = (value = 480.0; unit = "kPa");
        attribute reseatPressure : Pressure = (value = 430.0; unit = "kPa");

        port inlet : FluidInletPort;
        port outlet : FluidOutletPort;
    }

    part def SensorSet {
        port flowTap : FluidOutletPort;
        port pressureTap : FluidOutletPort;
        port temperatureTap : TelemetryOutputPort;
        port telemetryPort : TelemetryOutputPort;

        part flowSensor : FlowSensor;
        part pressureSensor : PressureSensor;
        part temperatureSensor : TemperatureSensor;
        part vibrationSensor : VibrationSensor;
    }

    part def FlowSensor {
        attribute range : FlowRate = (value = 200.0; unit = "L/min");
        attribute accuracyPercentOfReading : Real = 1.0;
    }

    part def PressureSensor {
        attribute range : Pressure = (value = 700.0; unit = "kPa");
        attribute accuracyPercentFullScale : Real = 0.5;
    }

    part def TemperatureSensor {
        attribute rangeMinimum : Temperature = (value = -10.0; unit = "degC");
        attribute rangeMaximum : Temperature = (value = 90.0; unit = "degC");
    }

    part def VibrationSensor {
        attribute alarmThreshold : Real = 7.1;
        attribute unit : String = "mm/s RMS";
    }

    part def PumpController {
        attribute minimumStartLevel : Real = 0.35;
        attribute levelUnit : String = "m";
        attribute lowFlowTripDelay : Real = 10.0;
        attribute delayUnit : String = "s";

        port commandPort : ControlInputPort;
        port motorCommandPort : ControlInputPort;

        perform behavior controlBehavior : PumpControlStateMachine;
    }

    part def LubricationSystem {
        attribute reservoirVolume : Real = 0.75;
        attribute reservoirVolumeUnit : String = "L";
        attribute serviceIntervalHours : Real = 1000.0;

        port lubeOutlet : LubricantPort;
    }

    action def StartPump {
        in attribute requestedSpeed : RotationalSpeed;
        out attribute startAccepted : Boolean;
    }

    action def StopPump {
        out attribute stopped : Boolean;
    }

    action def RegulateSpeed {
        in attribute flowSetpoint : FlowRate;
        in attribute measuredFlow : FlowRate;
        out attribute commandedSpeed : RotationalSpeed;
    }

    action def DetectFaults {
        in attribute measuredPressure : Pressure;
        in attribute measuredFlow : FlowRate;
        in attribute measuredTemperature : Temperature;
        out attribute faultPresent : Boolean;
        out attribute faultCode : String;
    }

    action def MoveFluidByChainBuckets {
        in item inletFluid : WorkingFluid;
        in attribute shaftSpeed : RotationalSpeed;
        out item outletFluid : WorkingFluid;
        out attribute deliveredFlow : FlowRate;
        out attribute developedPressure : Pressure;
    }

    behavior def PumpingOperation {
        in item sourceFluid : WorkingFluid;
        out item deliveredFluid : WorkingFluid;

        action start : StartPump;
        action lift : MoveFluidByChainBuckets;
        action regulate : RegulateSpeed;
        action detect : DetectFaults;

        flow start.startAccepted to lift;
        flow lift.deliveredFlow to regulate.measuredFlow;
        flow lift.developedPressure to detect.measuredPressure;
        flow sourceFluid to lift.inletFluid;
        flow lift.outletFluid to deliveredFluid;
    }

    state def PumpControlStateMachine {
        entry action initialize {
            attribute initialized : Boolean = true;
        }

        state Off;
        state Ready;
        state Priming;
        state Running;
        state LowFlowRecovery;
        state Faulted;
        state MaintenanceLockout;

        initial then Off;

        transition Off_to_Ready
            first Off
            then Ready
            accept ControlSignal
            if command == "ENABLE" and enable == true;

        transition Ready_to_Priming
            first Ready
            then Priming
            accept ControlSignal
            if command == "START";

        transition Priming_to_Running
            first Priming
            then Running
            if true;

        transition Running_to_LowFlowRecovery
            first Running
            then LowFlowRecovery
            accept SensorSignal
            if measuredFlow.value < 80.0 and faultActive == false;

        transition LowFlowRecovery_to_Running
            first LowFlowRecovery
            then Running
            accept SensorSignal
            if measuredFlow.value >= 100.0;

        transition Running_to_Faulted
            first Running
            then Faulted
            accept SensorSignal
            if faultActive == true or measuredPressure.value > 500.0 or measuredTemperature.value > 60.0;

        transition LowFlowRecovery_to_Faulted
            first LowFlowRecovery
            then Faulted
            accept SensorSignal
            if faultActive == true;

        transition Faulted_to_Ready
            first Faulted
            then Ready
            accept ControlSignal
            if command == "RESET" and enable == true;

        transition Ready_to_Off
            first Ready
            then Off
            accept ControlSignal
            if command == "DISABLE" or enable == false;

        transition Running_to_Ready
            first Running
            then Ready
            accept ControlSignal
            if command == "STOP";

        transition Ready_to_MaintenanceLockout
            first Ready
            then MaintenanceLockout
            accept ControlSignal
            if command == "LOCKOUT";

        transition MaintenanceLockout_to_Off
            first MaintenanceLockout
            then Off
            accept ControlSignal
            if command == "UNLOCK";
    }

    requirement def FlowCapacityRequirement {
        subject subsystem : ChainPumpSubsystem;
        require constraint {
            subsystem.outlet.deliveredFlow.value >= 120.0
        }
    }

    requirement def DischargePressureRequirement {
        subject subsystem : ChainPumpSubsystem;
        require constraint {
            subsystem.outlet.dischargePressure.value >= 350.0
        }
    }

    requirement def OverpressureProtectionRequirement {
        subject valve : ReliefValve;
        require constraint {
            valve.setPressure.value <= 480.0
        }
    }

    requirement def ChainSpeedLimitRequirement {
        subject pump : ChainPump;
        require constraint {
            pump.nominalSpeed.value <= pump.maximumSpeed.value
        }
    }

    requirement def SealLeakageRequirement {
        subject seal : ShaftSeal;
        require constraint {
            seal.maximumLeakage.value <= 0.05
        }
    }

    requirement def GuardingRequirement {
        subject guard : GuardAssembly;
        require constraint {
            guard.removableWithToolOnly == true and guard.interlockInstalled == true
        }
    }

    requirement def TemperatureRequirement {
        subject subsystem : ChainPumpSubsystem;
        require constraint {
            subsystem.maximumFluidTemperature.value <= 60.0
        }
    }

    requirement def EfficiencyRequirement {
        subject subsystem : ChainPumpSubsystem;
        require constraint {
            subsystem.nominalEfficiency.value >= 70.0
        }
    }

    requirement def MaintenanceRequirement {
        subject lubrication : LubricationSystem;
        require constraint {
            lubrication.serviceIntervalHours >= 1000.0
        }
    }

    part chainPumpSubsystem : ChainPumpSubsystem;

    satisfy FlowCapacityRequirement by chainPumpSubsystem;
    satisfy DischargePressureRequirement by chainPumpSubsystem;
    satisfy TemperatureRequirement by chainPumpSubsystem;
    satisfy EfficiencyRequirement by chainPumpSubsystem;
    satisfy OverpressureProtectionRequirement by chainPumpSubsystem.pressureReliefValve;
    satisfy ChainSpeedLimitRequirement by chainPumpSubsystem.chainPump;
    satisfy SealLeakageRequirement by chainPumpSubsystem.chainPump.shaftSeal;
    satisfy GuardingRequirement by chainPumpSubsystem.chainGuard;
    satisfy MaintenanceRequirement by chainPumpSubsystem.lubricationSystem;
}

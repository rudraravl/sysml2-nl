package SpacecraftAttitudeControlModel {

  import ScalarValues::*;
  import SI::*;
  import ISQ::*;

  attribute def Angle :> ISQ::planeAngle {
    doc /* Angular displacement used for attitude, pointing, and error budgets. */
  }

  attribute def AngularRate :> ISQ::angularVelocity {
    doc /* Rotational rate about a spacecraft body axis. */
  }

  attribute def Torque :> ISQ::torque {
    doc /* Control torque generated by actuators. */
  }

  attribute def Force :> ISQ::force {
    doc /* Translational force generated by thrusters. */
  }

  attribute def Voltage :> ISQ::electricPotential {
    doc /* Electrical potential at a power interface. */
  }

  attribute def Current :> ISQ::electricCurrent {
    doc /* Electrical current drawn or supplied at a power interface. */
  }

  attribute def Power :> ISQ::power {
    doc /* Electrical power available to or consumed by equipment. */
  }

  attribute def Mass :> ISQ::mass {
    doc /* Equipment or propellant mass. */
  }

  attribute def TimeDuration :> ISQ::time {
    doc /* Time interval used for control cycles, state timing, and fault timers. */
  }

  attribute def DataRate :> ISQ::frequency {
    doc /* Logical telemetry or command transfer rate. */
  }

  attribute def MagneticDipoleMoment {
    attribute value : Real;
    doc /* Magnetic dipole moment in ampere square meters. */
  }

  enum def ACSMode {
    enum Off;
    enum Standby;
    enum Detumble;
    enum SunPointing;
    enum NadirPointing;
    enum InertialPointing;
    enum MomentumManagement;
    enum SafeHold;
    enum FaultIsolation;
  }

  enum def SensorHealth {
    enum Nominal;
    enum Degraded;
    enum Failed;
  }

  enum def ActuatorHealth {
    enum Nominal;
    enum Saturated;
    enum Failed;
  }

  enum def PointingFrame {
    enum Body;
    enum InertialJ2000;
    enum LocalVerticalLocalHorizontal;
    enum SunVector;
    enum TargetLineOfSight;
  }

  item def AttitudeQuaternion {
    attribute q0 : Real;
    attribute q1 : Real;
    attribute q2 : Real;
    attribute q3 : Real;
    constraint unitNorm {
      q0*q0 + q1*q1 + q2*q2 + q3*q3 == 1.0
    }
    doc /* Unit quaternion representing spacecraft body attitude relative to a selected reference frame. */
  }

  item def BodyAngularRate {
    attribute wx : AngularRate;
    attribute wy : AngularRate;
    attribute wz : AngularRate;
    doc /* Spacecraft body angular velocity resolved in body coordinates. */
  }

  item def AttitudeState {
    attribute attitude : AttitudeQuaternion;
    attribute bodyRate : BodyAngularRate;
    attribute covarianceTrace : Real;
    attribute timeTag : TimeDuration;
    doc /* Estimated spacecraft attitude, angular rate, uncertainty, and time tag. */
  }

  item def AttitudeSetpoint {
    attribute commandedAttitude : AttitudeQuaternion;
    attribute commandedRate : BodyAngularRate;
    attribute frame : PointingFrame;
    attribute maximumAllowedError : Angle;
    attribute validityDuration : TimeDuration;
    doc /* High-level commanded pointing objective used by the attitude controller. */
  }

  item def StarTrackerMeasurement {
    attribute measuredAttitude : AttitudeQuaternion;
    attribute residualError : Angle;
    attribute integrationTime : TimeDuration;
    attribute health : SensorHealth;
    doc /* Absolute attitude measurement produced by a star tracker. */
  }

  item def GyroscopeMeasurement {
    attribute measuredRate : BodyAngularRate;
    attribute biasX : AngularRate;
    attribute biasY : AngularRate;
    attribute biasZ : AngularRate;
    attribute noiseDensity : Real;
    attribute health : SensorHealth;
    doc /* Body angular rate measurement with estimated bias terms. */
  }

  item def SunSensorMeasurement {
    attribute sunVectorBodyX : Real;
    attribute sunVectorBodyY : Real;
    attribute sunVectorBodyZ : Real;
    attribute sunAngleConfidence : Real;
    attribute health : SensorHealth;
    doc /* Unit sun vector measurement resolved in spacecraft body coordinates. */
  }

  item def MagnetometerMeasurement {
    attribute magneticFieldBodyX : Real;
    attribute magneticFieldBodyY : Real;
    attribute magneticFieldBodyZ : Real;
    attribute health : SensorHealth;
    doc /* Local geomagnetic field vector measurement resolved in body coordinates. */
  }

  item def WheelTorqueCommand {
    attribute torqueX : Torque;
    attribute torqueY : Torque;
    attribute torqueZ : Torque;
    attribute torqueMagnitudeLimit : Torque;
    doc /* Requested torque vector to be distributed to reaction wheels. */
  }

  item def ThrusterPulseCommand {
    attribute pulseWidth : TimeDuration;
    attribute forceLevel : Force;
    attribute rollPulseEnable : Boolean;
    attribute pitchPulseEnable : Boolean;
    attribute yawPulseEnable : Boolean;
    doc /* Discrete thruster pulse command used for safe mode or momentum unloading. */
  }

  item def MagnetorquerCommand {
    attribute dipoleX : MagneticDipoleMoment;
    attribute dipoleY : MagneticDipoleMoment;
    attribute dipoleZ : MagneticDipoleMoment;
    doc /* Magnetic dipole command used for detumbling and wheel desaturation. */
  }

  item def TelemetryPacket {
    attribute currentMode : ACSMode;
    attribute estimatedAttitudeError : Angle;
    attribute estimatedRateNorm : AngularRate;
    attribute wheelMomentumMargin : Real;
    attribute activeFaultCount : Integer;
    attribute packetTime : TimeDuration;
    doc /* Attitude control subsystem telemetry reported to spacecraft avionics. */
  }

  item def ModeCommand {
    attribute requestedMode : ACSMode;
    attribute setpoint : AttitudeSetpoint;
    attribute commandTime : TimeDuration;
    doc /* Command from spacecraft avionics selecting attitude-control mode and target attitude. */
  }

  item def ElectricalPower {
    attribute voltage : Voltage;
    attribute current : Current;
    attribute availablePower : Power;
    doc /* Regulated spacecraft bus power supplied to attitude-control equipment. */
  }

  item def ThermalStatus {
    attribute electronicsTemperature : ISQ::thermodynamicTemperature;
    attribute actuatorTemperature : ISQ::thermodynamicTemperature;
    attribute withinOperatingLimits : Boolean;
    doc /* Thermal condition of the attitude-control subsystem. */
  }

  port def PowerInputPort {
    in item powerIn : ElectricalPower;
  }

  port def CommandInputPort {
    in item commandIn : ModeCommand;
  }

  port def TelemetryOutputPort {
    out item telemetryOut : TelemetryPacket;
  }

  port def StarTrackerMeasurementPort {
    out item starTrackerMeasurementOut : StarTrackerMeasurement;
  }

  port def GyroscopeMeasurementPort {
    out item gyroMeasurementOut : GyroscopeMeasurement;
  }

  port def SunSensorMeasurementPort {
    out item sunSensorMeasurementOut : SunSensorMeasurement;
  }

  port def MagnetometerMeasurementPort {
    out item magnetometerMeasurementOut : MagnetometerMeasurement;
  }

  port def AttitudeStateOutputPort {
    out item attitudeStateOut : AttitudeState;
  }

  port def AttitudeStateInputPort {
    in item attitudeStateIn : AttitudeState;
  }

  port def WheelCommandOutputPort {
    out item wheelCommandOut : WheelTorqueCommand;
  }

  port def WheelCommandInputPort {
    in item wheelCommandIn : WheelTorqueCommand;
  }

  port def ThrusterCommandOutputPort {
    out item thrusterCommandOut : ThrusterPulseCommand;
  }

  port def ThrusterCommandInputPort {
    in item thrusterCommandIn : ThrusterPulseCommand;
  }

  port def MagnetorquerCommandOutputPort {
    out item magnetorquerCommandOut : MagnetorquerCommand;
  }

  port def MagnetorquerCommandInputPort {
    in item magnetorquerCommandIn : MagnetorquerCommand;
  }

  port def ThermalStatusPort {
    out item thermalStatusOut : ThermalStatus;
  }

  action def AcquireSensorData {
    in item starTrackerMeasurement : StarTrackerMeasurement;
    in item gyroMeasurement : GyroscopeMeasurement;
    in item sunSensorMeasurement : SunSensorMeasurement;
    in item magnetometerMeasurement : MagnetometerMeasurement;
    out item validatedStarTrackerMeasurement : StarTrackerMeasurement;
    out item validatedGyroMeasurement : GyroscopeMeasurement;
    out item validatedSunSensorMeasurement : SunSensorMeasurement;
    out item validatedMagnetometerMeasurement : MagnetometerMeasurement;
    doc /* Collects raw attitude sensor data, performs health screening, and forwards validated measurements. */
  }

  action def EstimateAttitude {
    in item starTrackerMeasurement : StarTrackerMeasurement;
    in item gyroMeasurement : GyroscopeMeasurement;
    in item sunSensorMeasurement : SunSensorMeasurement;
    in item magnetometerMeasurement : MagnetometerMeasurement;
    out item estimatedState : AttitudeState;
    attribute propagationPeriod : TimeDuration = 0.1 [SI::s];
    doc /* Fuses absolute attitude, angular-rate, sun-vector, and magnetic-field observations into a spacecraft attitude estimate. */
  }

  action def ComputePointingError {
    in item estimatedState : AttitudeState;
    in item setpoint : AttitudeSetpoint;
    out attribute pointingError : Angle;
    out item rateError : BodyAngularRate;
    doc /* Compares commanded attitude with estimated attitude to determine pointing and rate errors. */
  }

  action def GenerateControlTorque {
    in attribute pointingError : Angle;
    in item rateError : BodyAngularRate;
    in item estimatedState : AttitudeState;
    out item wheelTorqueCommand : WheelTorqueCommand;
    attribute proportionalGain : Real = 0.85;
    attribute derivativeGain : Real = 1.45;
    doc /* Computes closed-loop three-axis torque demand for precision attitude pointing. */
  }

  action def PerformDetumbleControl {
    in item gyroMeasurement : GyroscopeMeasurement;
    in item magnetometerMeasurement : MagnetometerMeasurement;
    out item magnetorquerCommand : MagnetorquerCommand;
    attribute bDotGain : Real = 25000.0;
    doc /* Uses magnetic B-dot damping to reduce spacecraft angular rate after deployment or anomaly recovery. */
  }

  action def ManageWheelMomentum {
    in item estimatedState : AttitudeState;
    out item magnetorquerCommand : MagnetorquerCommand;
    out item thrusterPulseCommand : ThrusterPulseCommand;
    attribute wheelMomentumHighThreshold : Real = 0.85;
    attribute wheelMomentumLowThreshold : Real = 0.55;
    doc /* Desaturates reaction wheels using magnetorquers or thrusters while preserving pointing stability. */
  }

  action def EnterSafeHold {
    in item sunSensorMeasurement : SunSensorMeasurement;
    in item gyroMeasurement : GyroscopeMeasurement;
    out item wheelTorqueCommand : WheelTorqueCommand;
    out item magnetorquerCommand : MagnetorquerCommand;
    out item telemetry : TelemetryPacket;
    doc /* Establishes a power-positive safe attitude using sun-vector knowledge and rate damping. */
  }

  action def PublishTelemetry {
    in item estimatedState : AttitudeState;
    in attribute currentMode : ACSMode;
    in attribute activeFaultCount : Integer;
    out item telemetry : TelemetryPacket;
    doc /* Formats mode, health, pointing, and momentum data for spacecraft avionics. */
  }

  state def AttitudeControlModeMachine {
    attribute activeMode : ACSMode = ACSMode::Standby;
    attribute rateNorm : AngularRate;
    attribute pointingError : Angle;
    attribute faultCount : Integer = 0;
    attribute wheelMomentumMargin : Real = 1.0;

    entry action initializeMode {
      activeMode = ACSMode::Standby;
    }

    state Off {
      entry action setOff {
        activeMode = ACSMode::Off;
      }
    }

    state Standby {
      entry action setStandby {
        activeMode = ACSMode::Standby;
      }
    }

    state Detumble {
      entry action setDetumble {
        activeMode = ACSMode::Detumble;
      }
      do action performRateDamping : PerformDetumbleControl;
    }

    state SunPointing {
      entry action setSunPointing {
        activeMode = ACSMode::SunPointing;
      }
      do action maintainPowerPositiveAttitude : GenerateControlTorque;
    }

    state NadirPointing {
      entry action setNadirPointing {
        activeMode = ACSMode::NadirPointing;
      }
      do action maintainEarthPointing : GenerateControlTorque;
    }

    state InertialPointing {
      entry action setInertialPointing {
        activeMode = ACSMode::InertialPointing;
      }
      do action maintainPrecisionTargetPointing : GenerateControlTorque;
    }

    state MomentumManagement {
      entry action setMomentumManagement {
        activeMode = ACSMode::MomentumManagement;
      }
      do action unloadStoredMomentum : ManageWheelMomentum;
    }

    state SafeHold {
      entry action setSafeHold {
        activeMode = ACSMode::SafeHold;
      }
      do action holdSafeSunAttitude : EnterSafeHold;
    }

    state FaultIsolation {
      entry action setFaultIsolation {
        activeMode = ACSMode::FaultIsolation;
      }
    }

    transition initialStandby first Standby;

    transition standbyToDetumble
      first Standby
      then Detumble
      if rateNorm > 0.5 [SI::rad_per_s];

    transition detumbleToSunPointing
      first Detumble
      then SunPointing
      if rateNorm <= 0.02 [SI::rad_per_s];

    transition sunPointingToInertialPointing
      first SunPointing
      then InertialPointing
      if pointingError <= 1.0 [SI::deg];

    transition inertialToNadir
      first InertialPointing
      then NadirPointing
      if activeMode == ACSMode::NadirPointing;

    transition pointingToMomentumManagement
      first InertialPointing
      then MomentumManagement
      if wheelMomentumMargin < 0.15;

    transition momentumManagementToInertial
      first MomentumManagement
      then InertialPointing
      if wheelMomentumMargin > 0.45;

    transition anyNominalToSafeHold
      first SunPointing
      then SafeHold
      if faultCount >= 2;

    transition inertialFaultToSafeHold
      first InertialPointing
      then SafeHold
      if faultCount >= 2;

    transition safeHoldToFaultIsolation
      first SafeHold
      then FaultIsolation
      if faultCount >= 4;

    transition faultIsolationToStandby
      first FaultIsolation
      then Standby
      if faultCount == 0;
  }

  part def StarTracker {
    attribute mass : Mass = 3.2 [SI::kg];
    attribute nominalPower : Power = 12.0 [SI::W];
    attribute fieldOfView : Angle = 20.0 [SI::deg];
    attribute updatePeriod : TimeDuration = 0.5 [SI::s];
    attribute attitudeAccuracy : Angle = 0.003 [SI::deg];
    attribute health : SensorHealth = SensorHealth::Nominal;
    port powerPort : PowerInputPort;
    port measurementPort : StarTrackerMeasurementPort;
    doc /* Optical sensor providing high-accuracy absolute attitude when stars are visible. */
  }

  part def InertialMeasurementUnit {
    attribute mass : Mass = 2.1 [SI::kg];
    attribute nominalPower : Power = 8.0 [SI::W];
    attribute updatePeriod : TimeDuration = 0.01 [SI::s];
    attribute angularRandomWalk : Real = 0.005;
    attribute maximumRate : AngularRate = 10.0 [SI::rad_per_s];
    attribute health : SensorHealth = SensorHealth::Nominal;
    port powerPort : PowerInputPort;
    port measurementPort : GyroscopeMeasurementPort;
    doc /* Three-axis gyroscope assembly measuring spacecraft body rates for propagation and damping. */
  }

  part def CoarseSunSensorAssembly {
    attribute mass : Mass = 1.4 [SI::kg];
    attribute nominalPower : Power = 3.0 [SI::W];
    attribute sunVectorAccuracy : Angle = 2.0 [SI::deg];
    attribute updatePeriod : TimeDuration = 0.25 [SI::s];
    attribute health : SensorHealth = SensorHealth::Nominal;
    port powerPort : PowerInputPort;
    port measurementPort : SunSensorMeasurementPort;
    doc /* Distributed coarse sun sensors used for safe hold and power-positive acquisition. */
  }

  part def ThreeAxisMagnetometer {
    attribute mass : Mass = 0.8 [SI::kg];
    attribute nominalPower : Power = 1.5 [SI::W];
    attribute updatePeriod : TimeDuration = 0.1 [SI::s];
    attribute fieldNoise : Real = 25.0;
    attribute health : SensorHealth = SensorHealth::Nominal;
    port powerPort : PowerInputPort;
    port measurementPort : MagnetometerMeasurementPort;
    doc /* Magnetic field sensor supporting detumble and magnetic torquer control. */
  }

  part def AttitudeDeterminationComputer {
    attribute mass : Mass = 4.5 [SI::kg];
    attribute nominalPower : Power = 35.0 [SI::W];
    attribute estimationCycle : TimeDuration = 0.1 [SI::s];
    attribute maximumAttitudeKnowledgeError : Angle = 0.05 [SI::deg];
    attribute processorUtilization : Real = 0.38;
    port powerPort : PowerInputPort;
    port starTrackerInput : StarTrackerMeasurementPort;
    port gyroInput : GyroscopeMeasurementPort;
    port sunSensorInput : SunSensorMeasurementPort;
    port magnetometerInput : MagnetometerMeasurementPort;
    port estimatedStateOutput : AttitudeStateOutputPort;
    perform action sensorAcquisition : AcquireSensorData;
    perform action attitudeEstimation : EstimateAttitude;
    doc /* Onboard processing unit that validates sensor data and estimates spacecraft attitude state. */
  }

  part def AttitudeControlComputer {
    attribute mass : Mass = 3.8 [SI::kg];
    attribute nominalPower : Power = 28.0 [SI::W];
    attribute controlCycle : TimeDuration = 0.1 [SI::s];
    attribute pointingControlBandwidth : Real = 0.08;
    attribute commandedMode : ACSMode = ACSMode::Standby;
    port powerPort : PowerInputPort;
    port commandInput : CommandInputPort;
    port attitudeStateInput : AttitudeStateInputPort;
    port wheelCommandOutput : WheelCommandOutputPort;
    port thrusterCommandOutput : ThrusterCommandOutputPort;
    port magnetorquerCommandOutput : MagnetorquerCommandOutputPort;
    port telemetryOutput : TelemetryOutputPort;
    perform action computeError : ComputePointingError;
    perform action closedLoopTorqueGeneration : GenerateControlTorque;
    perform action detumbleControl : PerformDetumbleControl;
    perform action wheelMomentumManagement : ManageWheelMomentum;
    perform action safeHoldControl : EnterSafeHold;
    perform action telemetryGeneration : PublishTelemetry;
    exhibit state modeLogic : AttitudeControlModeMachine;
    doc /* Executes attitude-control laws, manages operating modes, commands actuators, and reports status. */
  }

  part def ReactionWheelAssembly {
    attribute mass : Mass = 18.0 [SI::kg];
    attribute nominalPower : Power = 55.0 [SI::W];
    attribute peakPower : Power = 180.0 [SI::W];
    attribute maximumTorquePerAxis : Torque = 0.18 [SI::N_m];
    attribute storedMomentumCapacity : Real = 45.0;
    attribute wheelCount : Integer = 4;
    attribute health : ActuatorHealth = ActuatorHealth::Nominal;
    port powerPort : PowerInputPort;
    port commandInput : WheelCommandInputPort;
    doc /* Four-wheel pyramid assembly producing precise three-axis control torque. */
  }

  part def MagnetorquerAssembly {
    attribute mass : Mass = 5.0 [SI::kg];
    attribute nominalPower : Power = 18.0 [SI::W];
    attribute maximumDipolePerAxis : MagneticDipoleMoment;
    attribute health : ActuatorHealth = ActuatorHealth::Nominal;
    port powerPort : PowerInputPort;
    port commandInput : MagnetorquerCommandInputPort;
    doc /* Three-axis magnetic torque rods used for detumbling and reaction-wheel momentum unloading. */
  }

  part def ReactionControlThrusterSet {
    attribute dryMass : Mass = 11.0 [SI::kg];
    attribute propellantMass : Mass = 22.0 [SI::kg];
    attribute minimumImpulseBit : Real = 0.08;
    attribute thrustPerThruster : Force = 1.0 [SI::N];
    attribute thrusterCount : Integer = 8;
    attribute health : ActuatorHealth = ActuatorHealth::Nominal;
    port commandInput : ThrusterCommandInputPort;
    doc /* Redundant thruster set providing coarse attitude torques during safe mode and momentum unloading. */
  }

  part def PowerDistributionUnit {
    attribute regulatedVoltage : Voltage = 28.0 [SI::V];
    attribute maximumContinuousPower : Power = 400.0 [SI::W];
    attribute currentLimit : Current = 20.0 [SI::A];
    port spacecraftPowerInput : PowerInputPort;
    port starTrackerPower : PowerInputPort;
    port imuPower : PowerInputPort;
    port sunSensorPower : PowerInputPort;
    port magnetometerPower : PowerInputPort;
    port determinationComputerPower : PowerInputPort;
    port controlComputerPower : PowerInputPort;
    port wheelPower : PowerInputPort;
    port magnetorquerPower : PowerInputPort;
    doc /* Distributes regulated bus power to attitude-control sensors, computers, and actuators. */
  }

  part def ThermalMonitor {
    attribute mass : Mass = 0.6 [SI::kg];
    attribute nominalPower : Power = 1.0 [SI::W];
    attribute minimumOperatingTemperature : ISQ::thermodynamicTemperature = 253.15 [SI::K];
    attribute maximumOperatingTemperature : ISQ::thermodynamicTemperature = 323.15 [SI::K];
    port thermalStatusOutput : ThermalStatusPort;
    doc /* Monitors thermal state of attitude-control electronics and actuators. */
  }

  part def SpacecraftAttitudeControlSystem {
    attribute totalMass : Mass = 80.4 [SI::kg];
    attribute nominalPowerConsumption : Power = 161.5 [SI::W];
    attribute peakPowerConsumption : Power = 320.0 [SI::W];
    attribute primaryFunction : String =
      "Determine spacecraft attitude, compare it with commanded pointing objectives, and generate actuator commands that orient and stabilize the spacecraft in three axes.";
    attribute maximumSteadyStatePointingError : Angle = 0.10 [SI::deg];
    attribute maximumSafeModeRate : AngularRate = 0.02 [SI::rad_per_s];
    attribute controlUpdatePeriod : TimeDuration = 0.1 [SI::s];
    attribute availability : Real = 0.995;

    port spacecraftPowerInput : PowerInputPort;
    port spacecraftCommandInput : CommandInputPort;
    port spacecraftTelemetryOutput : TelemetryOutputPort;

    part powerDistributionUnit : PowerDistributionUnit;
    part starTracker : StarTracker;
    part inertialMeasurementUnit : InertialMeasurementUnit;
    part sunSensorAssembly : CoarseSunSensorAssembly;
    part magnetometer : ThreeAxisMagnetometer;
    part attitudeDeterminationComputer : AttitudeDeterminationComputer;
    part attitudeControlComputer : AttitudeControlComputer;
    part reactionWheelAssembly : ReactionWheelAssembly;
    part magnetorquerAssembly : MagnetorquerAssembly;
    part reactionControlThrusterSet : ReactionControlThrusterSet;
    part thermalMonitor : ThermalMonitor;

    connect spacecraftPowerInput to powerDistributionUnit.spacecraftPowerInput;

    connect powerDistributionUnit.starTrackerPower to starTracker.powerPort;
    connect powerDistributionUnit.imuPower to inertialMeasurementUnit.powerPort;
    connect powerDistributionUnit.sunSensorPower to sunSensorAssembly.powerPort;
    connect powerDistributionUnit.magnetometerPower to magnetometer.powerPort;
    connect powerDistributionUnit.determinationComputerPower to attitudeDeterminationComputer.powerPort;
    connect powerDistributionUnit.controlComputerPower to attitudeControlComputer.powerPort;
    connect powerDistributionUnit.wheelPower to reactionWheelAssembly.powerPort;
    connect powerDistributionUnit.magnetorquerPower to magnetorquerAssembly.powerPort;

    connect starTracker.measurementPort to attitudeDeterminationComputer.starTrackerInput;
    connect inertialMeasurementUnit.measurementPort to attitudeDeterminationComputer.gyroInput;
    connect sunSensorAssembly.measurementPort to attitudeDeterminationComputer.sunSensorInput;
    connect magnetometer.measurementPort to attitudeDeterminationComputer.magnetometerInput;

    connect attitudeDeterminationComputer.estimatedStateOutput to attitudeControlComputer.attitudeStateInput;
    connect spacecraftCommandInput to attitudeControlComputer.commandInput;
    connect attitudeControlComputer.wheelCommandOutput to reactionWheelAssembly.commandInput;
    connect attitudeControlComputer.magnetorquerCommandOutput to magnetorquerAssembly.commandInput;
    connect attitudeControlComputer.thrusterCommandOutput to reactionControlThrusterSet.commandInput;
    connect attitudeControlComputer.telemetryOutput to spacecraftTelemetryOutput;

    doc /* Spacecraft attitude-control subsystem that provides closed-loop three-axis pointing and stabilization for mission operations and safe recovery. */
  }

  requirement def PrimaryFunctionRequirement {
    subject acs : SpacecraftAttitudeControlSystem;
    require constraint primaryFunctionDefined {
      acs.primaryFunction ==
      "Determine spacecraft attitude, compare it with commanded pointing objectives, and generate actuator commands that orient and stabilize the spacecraft in three axes."
    }
    doc /* The system shall provide a high-level attitude-control function that determines attitude, computes control errors, and commands actuators for three-axis stabilization. */
  }

  requirement def AttitudeKnowledgeRequirement {
    subject acs : SpacecraftAttitudeControlSystem;
    require constraint knowledgeAccuracy {
      acs.attitudeDeterminationComputer.maximumAttitudeKnowledgeError <= 0.05 [SI::deg]
    }
    doc /* The attitude determination function shall estimate attitude with knowledge error not greater than 0.05 degrees during nominal star-tracker-aided operation. */
  }

  requirement def PointingAccuracyRequirement {
    subject acs : SpacecraftAttitudeControlSystem;
    require constraint pointingAccuracy {
      acs.maximumSteadyStatePointingError <= 0.10 [SI::deg]
    }
    doc /* The attitude-control system shall maintain steady-state pointing error within 0.10 degrees in inertial or nadir pointing modes. */
  }

  requirement def ControlCycleRequirement {
    subject acs : SpacecraftAttitudeControlSystem;
    require constraint controlPeriod {
      acs.controlUpdatePeriod <= 0.1 [SI::s]
    }
    doc /* The control computer shall update actuator commands at least every 0.1 seconds during closed-loop control. */
  }

  requirement def DetumbleRequirement {
    subject acs : SpacecraftAttitudeControlSystem;
    require constraint detumbleRate {
      acs.maximumSafeModeRate <= 0.02 [SI::rad_per_s]
    }
    doc /* After detumble completion, spacecraft body-rate magnitude shall be no greater than 0.02 radians per second. */
  }

  requirement def PowerRequirement {
    subject acs : SpacecraftAttitudeControlSystem;
    require constraint nominalPowerBudget {
      acs.nominalPowerConsumption <= 200.0 [SI::W]
    }
    require constraint peakPowerBudget {
      acs.peakPowerConsumption <= acs.powerDistributionUnit.maximumContinuousPower
    }
    doc /* The attitude-control subsystem shall remain within allocated nominal and peak electrical power budgets. */
  }

  requirement def ReactionWheelTorqueRequirement {
    subject acs : SpacecraftAttitudeControlSystem;
    require constraint wheelTorqueCapacity {
      acs.reactionWheelAssembly.maximumTorquePerAxis >= 0.15 [SI::N_m]
    }
    doc /* The reaction wheel assembly shall provide sufficient torque authority for precision three-axis pointing. */
  }

  requirement def SafeHoldRequirement {
    subject acs : SpacecraftAttitudeControlSystem;
    require constraint safeHoldSunSensorAvailable {
      acs.sunSensorAssembly.health != SensorHealth::Failed
    }
    require constraint safeHoldActuatorAvailable {
      acs.magnetorquerAssembly.health != ActuatorHealth::Failed
    }
    doc /* The system shall support safe-hold attitude control using sun sensors and magnetic torquers when precision sensors or wheels are unavailable. */
  }

  requirement def TelemetryRequirement {
    subject acs : SpacecraftAttitudeControlSystem;
    require constraint telemetryPortAvailable {
      acs.spacecraftTelemetryOutput != null
    }
    doc /* The system shall output attitude-control mode, pointing error, body-rate, momentum margin, and active fault count to spacecraft avionics. */
  }

  satisfy PrimaryFunctionRequirement by SpacecraftAttitudeControlSystem;
  satisfy AttitudeKnowledgeRequirement by AttitudeDeterminationComputer;
  satisfy PointingAccuracyRequirement by AttitudeControlComputer;
  satisfy ControlCycleRequirement by AttitudeControlComputer;
  satisfy DetumbleRequirement by MagnetorquerAssembly;
  satisfy PowerRequirement by PowerDistributionUnit;
  satisfy ReactionWheelTorqueRequirement by ReactionWheelAssembly;
  satisfy SafeHoldRequirement by CoarseSunSensorAssembly;
  satisfy SafeHoldRequirement by MagnetorquerAssembly;
  satisfy TelemetryRequirement by AttitudeControlComputer;

  part spacecraftACS : SpacecraftAttitudeControlSystem;

}

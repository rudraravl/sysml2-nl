package MerilLifeSciencesHighLevelSystem {

  import ScalarValues::*;
  import SI::*;

  attribute def Millimeter :> Real;
  attribute def Milliliter :> Real;
  attribute def MillimeterOfMercury :> Real;
  attribute def Newton :> Real;
  attribute def Second :> Real;
  attribute def Celsius :> Real;

  item def Patient {
    attribute identifier : String;
    attribute aorticAnnulusDiameter : Millimeter;
    attribute systolicPressure : MillimeterOfMercury;
    attribute diastolicPressure : MillimeterOfMercury;
  }

  item def SterileFluid {
    attribute volume : Milliliter;
    attribute temperature : Celsius;
  }

  item def Guidewire {
    attribute diameter : Millimeter;
    attribute usableLength : Millimeter;
  }

  item def CrimpedValve {
    attribute valveDiameter : Millimeter;
    attribute frameCompressionForce : Newton;
    attribute sterile : Boolean;
  }

  item def DeployedValve {
    attribute valveDiameter : Millimeter;
    attribute deployed : Boolean;
    attribute paravalvularLeakGrade : Integer;
    attribute meanGradient : MillimeterOfMercury;
  }

  item def HemodynamicData {
    attribute aorticPressure : MillimeterOfMercury;
    attribute ventricularPressure : MillimeterOfMercury;
    attribute heartRate : Integer;
    attribute timestamp : Second;
  }

  item def ImagingData {
    attribute annulusDiameter : Millimeter;
    attribute calcificationSeverity : Integer;
    attribute deploymentDepth : Millimeter;
  }

  item def ClinicalCommand {
    attribute commandName : String;
    attribute confirmedByOperator : Boolean;
  }

  port def VascularPort {
    in item guidewire : Guidewire;
    inout item crimpedValve : CrimpedValve;
    out item deployedValve : DeployedValve;
  }

  port def FluidPort {
    in item sterileFluid : SterileFluid;
  }

  port def DataPort {
    in item imaging : ImagingData;
    in item hemodynamics : HemodynamicData;
    out item command : ClinicalCommand;
  }

  port def MonitoringPort {
    out item hemodynamics : HemodynamicData;
    out item imaging : ImagingData;
  }

  part def MerilLifeSciencesTherapySystem {
    attribute primaryFunction : String =
      "Enable minimally invasive structural heart therapy by preparing, delivering, positioning, deploying, and verifying a transcatheter heart valve for restoration of aortic valve function.";

    attribute sterileBoundaryMaintained : Boolean;
    attribute maximumDeliveryTime : Second;
    attribute nominalValveDiameter : Millimeter;

    port vascularAccess : VascularPort;
    port rinseInput : FluidPort;
    port clinicalInterface : DataPort;
    port monitorInterface : MonitoringPort;

    part valveImplant : TranscatheterHeartValve;
    part deliveryCatheter : ValveDeliveryCatheter;
    part crimpingStation : ValveCrimpingStation;
    part flushingSet : SterileFlushSet;
    part operatorConsole : ProcedureControlConsole;
    part patientMonitor : HemodynamicAndImagingMonitor;

    connection guidewirePath connect vascularAccess to deliveryCatheter.distalAccess;
    connection valveLoadPath connect crimpingStation.outputPort to deliveryCatheter.valveInput;
    connection flushPath connect rinseInput to flushingSet.inputPort;
    connection catheterFlushPath connect flushingSet.outputPort to deliveryCatheter.flushPort;
    connection commandPath connect operatorConsole.commandPort to deliveryCatheter.controlPort;
    connection monitorPath connect patientMonitor.dataPort to operatorConsole.dataPort;
    connection systemDataPath connect monitorInterface to patientMonitor.externalPort;
    connection clinicalCommandPath connect clinicalInterface to operatorConsole.externalPort;

    perform action prepareAndDeliverValve;

    exhibit state TherapyLifecycle;

    satisfy requirement RestoreForwardFlow;
    satisfy requirement MaintainSterility;
    satisfy requirement VerifyDeployment;
  }

  part def TranscatheterHeartValve {
    attribute expandedDiameter : Millimeter;
    attribute crimpedDiameter : Millimeter;
    attribute frameRadialStrength : Newton;
    attribute leafletCount : Integer = 3;
    attribute biocompatible : Boolean = true;

    port implantPort : VascularPort;

    state ValveState {
      state Packaged;
      state Rinsed;
      state Crimped;
      state Loaded;
      state Positioned;
      state Deployed;
      state Verified;

      transition initial then Packaged;
      transition Packaged_to_Rinsed first Packaged then Rinsed;
      transition Rinsed_to_Crimped first Rinsed then Crimped;
      transition Crimped_to_Loaded first Crimped then Loaded;
      transition Loaded_to_Positioned first Loaded then Positioned;
      transition Positioned_to_Deployed first Positioned then Deployed;
      transition Deployed_to_Verified first Deployed then Verified;
    }
  }

  part def ValveDeliveryCatheter {
    attribute outerDiameter : Millimeter;
    attribute workingLength : Millimeter;
    attribute tipFlexibility : Newton;
    attribute deploymentDepthTarget : Millimeter;

    port distalAccess : VascularPort;
    port valveInput : VascularPort;
    port flushPort : FluidPort;
    port controlPort : DataPort;

    perform action navigateToAorticAnnulus;
    perform action deployImplant;
  }

  part def ValveCrimpingStation {
    attribute targetCrimpDiameter : Millimeter;
    attribute appliedCompressionForce : Newton;
    attribute crimpDuration : Second;

    port outputPort : VascularPort;

    perform action crimpValve;
  }

  part def SterileFlushSet {
    attribute primingVolume : Milliliter;
    attribute fluidTemperature : Celsius;

    port inputPort : FluidPort;
    port outputPort : FluidPort;

    perform action removeAirAndMaintainHydration;
  }

  part def ProcedureControlConsole {
    attribute operatorAuthorizationRequired : Boolean = true;
    attribute deploymentConfirmed : Boolean;

    port commandPort : DataPort;
    port dataPort : MonitoringPort;
    port externalPort : DataPort;

    perform action validateReadiness;
    perform action issueDeploymentCommand;
  }

  part def HemodynamicAndImagingMonitor {
    attribute minimumFrameRate : Integer;
    attribute pressureSamplingPeriod : Second;

    port dataPort : MonitoringPort;
    port externalPort : MonitoringPort;

    perform action acquireProcedureData;
    perform action assessValvePerformance;
  }

  action def prepareAndDeliverValve {
    in item patient : Patient;
    in item selectedValve : CrimpedValve;
    in item guidewire : Guidewire;
    out item implantedValve : DeployedValve;

    first start;
    then rinseValve;
    then crimpValve;
    then loadValve;
    then advanceCatheter;
    then positionAtAnnulus;
    then deployValve;
    then verifyHemodynamics;
    then finish;

    action rinseValve;
    action crimpValve;
    action loadValve;
    action advanceCatheter;
    action positionAtAnnulus;
    action deployValve;
    action verifyHemodynamics;
  }

  action def navigateToAorticAnnulus {
    in item guidewire : Guidewire;
    in item imaging : ImagingData;
    out item catheterAtTarget : Boolean;
  }

  action def deployImplant {
    in item command : ClinicalCommand;
    in item crimpedValve : CrimpedValve;
    out item deployedValve : DeployedValve;
  }

  action def crimpValve {
    in item valve : CrimpedValve;
    out item crimpedValve : CrimpedValve;
  }

  action def removeAirAndMaintainHydration {
    in item fluid : SterileFluid;
    out item primed : Boolean;
  }

  action def validateReadiness {
    in item imaging : ImagingData;
    in item hemodynamics : HemodynamicData;
    out item readyForDeployment : Boolean;
  }

  action def issueDeploymentCommand {
    in item readyForDeployment : Boolean;
    out item command : ClinicalCommand;
  }

  action def acquireProcedureData {
    out item imaging : ImagingData;
    out item hemodynamics : HemodynamicData;
  }

  action def assessValvePerformance {
    in item deployedValve : DeployedValve;
    in item hemodynamics : HemodynamicData;
    out item acceptableResult : Boolean;
  }

  state def TherapyLifecycle {
    state Configured;
    state SterilePrepared;
    state ValveLoaded;
    state Navigating;
    state Positioned;
    state Deploying;
    state HemodynamicVerification;
    state Completed;
    state AbortSafe;

    transition initial then Configured;
    transition prepare first Configured then SterilePrepared;
    transition load first SterilePrepared then ValveLoaded;
    transition navigate first ValveLoaded then Navigating;
    transition position first Navigating then Positioned;
    transition deploy first Positioned then Deploying;
    transition verify first Deploying then HemodynamicVerification;
    transition complete first HemodynamicVerification then Completed;
    transition abortFromPrepared first SterilePrepared then AbortSafe;
    transition abortFromNavigating first Navigating then AbortSafe;
    transition abortFromPositioned first Positioned then AbortSafe;
  }

  requirement def RestoreForwardFlow {
    subject system : MerilLifeSciencesTherapySystem;
    require constraint {
      system.valveImplant.leafletCount == 3
    }
  }

  requirement def MaintainSterility {
    subject system : MerilLifeSciencesTherapySystem;
    require constraint {
      system.sterileBoundaryMaintained == true
    }
  }

  requirement def VerifyDeployment {
    subject valve : DeployedValve;
    require constraint {
      valve.deployed == true and
      valve.meanGradient <= 20.0 and
      valve.paravalvularLeakGrade <= 1
    }
  }

  requirement def LimitDeliveryDuration {
    subject system : MerilLifeSciencesTherapySystem;
    require constraint {
      system.maximumDeliveryTime <= 1800.0
    }
  }

  part merilConceptSystem : MerilLifeSciencesTherapySystem {
    attribute sterileBoundaryMaintained = true;
    attribute maximumDeliveryTime = 1800.0;
    attribute nominalValveDiameter = 26.0;
  }
}

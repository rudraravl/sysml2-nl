package DesignAutomationConferenceSystem {
    import ScalarValues::*;
    import SI::*;

    attribute def PersonCount :> ScalarValues::Integer;
    attribute def SessionCount :> ScalarValues::Integer;
    attribute def BoothCount :> ScalarValues::Integer;
    attribute def PaperCount :> ScalarValues::Integer;
    attribute def CurrencyUSD :> ScalarValues::Real;
    attribute def DurationMinute :> ISQ::time;
    attribute def DateTimeValue :> ScalarValues::String;
    attribute def RoomCapacity :> ScalarValues::Integer;
    attribute def NetworkBandwidthMbps :> ScalarValues::Real;

    enum def RegistrationStatus {
        enum pending;
        enum approved;
        enum checkedIn;
        enum cancelled;
    }

    enum def SubmissionStatus {
        enum draft;
        enum submitted;
        enum underReview;
        enum accepted;
        enum rejected;
        enum scheduled;
        enum presented;
        enum archived;
    }

    enum def SessionType {
        enum keynote;
        enum technicalPaper;
        enum tutorial;
        enum panel;
        enum exhibitorDemo;
        enum workshop;
        enum networking;
    }

    enum def AccessDecision {
        enum granted;
        enum denied;
        enum manualReview;
    }

    item def AttendeeCredential {
        attribute badgeId : ScalarValues::String;
        attribute holderName : ScalarValues::String;
        attribute organization : ScalarValues::String;
        attribute status : RegistrationStatus;
    }

    item def PaperSubmission {
        attribute submissionId : ScalarValues::String;
        attribute title : ScalarValues::String;
        attribute authors : ScalarValues::String;
        attribute status : SubmissionStatus;
        attribute topicArea : ScalarValues::String;
    }

    item def ReviewDecision {
        attribute submissionId : ScalarValues::String;
        attribute score : ScalarValues::Real;
        attribute recommendation : SubmissionStatus;
    }

    item def ProgramSlot {
        attribute slotId : ScalarValues::String;
        attribute startTime : DateTimeValue;
        attribute duration : DurationMinute;
        attribute sessionType : SessionType;
        attribute roomName : ScalarValues::String;
    }

    item def BoothAssignment {
        attribute boothId : ScalarValues::String;
        attribute exhibitorName : ScalarValues::String;
        attribute hallZone : ScalarValues::String;
        attribute powerRequiredWatts : ScalarValues::Real;
    }

    item def AccessRequest {
        attribute credentialId : ScalarValues::String;
        attribute gateId : ScalarValues::String;
        attribute requestedArea : ScalarValues::String;
        attribute timestamp : DateTimeValue;
    }

    item def AccessResponse {
        attribute credentialId : ScalarValues::String;
        attribute decision : AccessDecision;
        attribute reason : ScalarValues::String;
    }

    item def ConferenceMetric {
        attribute registeredAttendees : PersonCount;
        attribute checkedInAttendees : PersonCount;
        attribute acceptedPapers : PaperCount;
        attribute activeSessions : SessionCount;
        attribute occupiedBooths : BoothCount;
        attribute revenueUSD : CurrencyUSD;
    }

    port def CredentialPort {
        in item credentialIn : AttendeeCredential;
        out item credentialOut : AttendeeCredential;
    }

    port def SubmissionPort {
        in item paperIn : PaperSubmission;
        out item paperOut : PaperSubmission;
    }

    port def ReviewPort {
        in item reviewIn : ReviewDecision;
        out item reviewOut : ReviewDecision;
    }

    port def SchedulePort {
        in item slotIn : ProgramSlot;
        out item slotOut : ProgramSlot;
    }

    port def BoothPort {
        in item boothIn : BoothAssignment;
        out item boothOut : BoothAssignment;
    }

    port def AccessControlPort {
        in item requestIn : AccessRequest;
        out item responseOut : AccessResponse;
    }

    port def MetricsPort {
        out item metricsOut : ConferenceMetric;
    }

    action def RegisterAttendee {
        in item credential : AttendeeCredential;
        out item registeredCredential : AttendeeCredential;
    }

    action def ReviewPaper {
        in item submission : PaperSubmission;
        out item decision : ReviewDecision;
    }

    action def ScheduleAcceptedPaper {
        in item submission : PaperSubmission;
        in item availableSlot : ProgramSlot;
        out item scheduledSlot : ProgramSlot;
    }

    action def AssignExhibitorBooth {
        in item boothRequest : BoothAssignment;
        out item confirmedBooth : BoothAssignment;
    }

    action def ValidateAccess {
        in item request : AccessRequest;
        in item credential : AttendeeCredential;
        out item response : AccessResponse;
    }

    state def ConferenceLifecycle {
        state Planning;
        state CallForPapersOpen;
        state ReviewInProgress;
        state ProgramPublished;
        state RegistrationOpen;
        state ConferenceActive;
        state ConferenceClosed;
        state ArchiveComplete;

        transition first Planning then CallForPapersOpen;
        transition CallForPapersOpen then ReviewInProgress;
        transition ReviewInProgress then ProgramPublished;
        transition ProgramPublished then RegistrationOpen;
        transition RegistrationOpen then ConferenceActive;
        transition ConferenceActive then ConferenceClosed;
        transition ConferenceClosed then ArchiveComplete;
    }

    part def PaperManagementSubsystem {
        attribute maximumSubmissions : PaperCount = 2500;
        attribute acceptedSubmissionTarget : PaperCount = 450;

        port submissions : SubmissionPort;
        port reviews : ReviewPort;
        port schedule : SchedulePort;

        action reviewPaper : ReviewPaper;
    }

    part def ProgramSchedulingSubsystem {
        attribute totalRooms : SessionCount = 42;
        attribute largestRoomCapacity : RoomCapacity = 3500;
        attribute minimumSessionDuration : DurationMinute = 20;
        attribute maximumSessionDuration : DurationMinute = 180;

        port acceptedPapers : SubmissionPort;
        port programSlots : SchedulePort;

        action scheduleAcceptedPaper : ScheduleAcceptedPaper;
    }

    part def AttendeeRegistrationSubsystem {
        attribute registrationCapacity : PersonCount = 12000;
        attribute standardPassPriceUSD : CurrencyUSD = 1295.00;
        attribute studentPassPriceUSD : CurrencyUSD = 295.00;

        port credentials : CredentialPort;
        port metrics : MetricsPort;

        action registerAttendee : RegisterAttendee;
    }

    part def ExhibitorManagementSubsystem {
        attribute availableBooths : BoothCount = 800;
        attribute exhibitHallBandwidth : NetworkBandwidthMbps = 10000.0;

        port booths : BoothPort;
        port metrics : MetricsPort;

        action assignExhibitorBooth : AssignExhibitorBooth;
    }

    part def AccessControlSubsystem {
        attribute entryGateCount : PersonCount = 24;
        attribute scanLatencyTarget : DurationMinute = 0.05;

        port credentials : CredentialPort;
        port access : AccessControlPort;

        action validateAccess : ValidateAccess;
    }

    part def ConferenceAnalyticsSubsystem {
        attribute reportingInterval : DurationMinute = 5;

        port registrationMetrics : MetricsPort;
        port exhibitorMetrics : MetricsPort;
        port conferenceMetrics : MetricsPort;
    }

    part def DesignAutomationConferenceAutomationSystem {
        attribute conferenceName : ScalarValues::String = "Design Automation Conference";
        attribute primaryFunction : ScalarValues::String =
            "Coordinate the Design Automation Conference by automating submission review, technical program scheduling, attendee registration, exhibitor logistics, access control, and operational reporting.";
        attribute plannedAttendance : PersonCount = 10000;
        attribute plannedTechnicalSessions : SessionCount = 300;
        attribute plannedExhibitorBooths : BoothCount = 650;

        part paperManagement : PaperManagementSubsystem;
        part programScheduling : ProgramSchedulingSubsystem;
        part attendeeRegistration : AttendeeRegistrationSubsystem;
        part exhibitorManagement : ExhibitorManagementSubsystem;
        part accessControl : AccessControlSubsystem;
        part analytics : ConferenceAnalyticsSubsystem;

        port externalSubmissionPortal : SubmissionPort;
        port externalRegistrationPortal : CredentialPort;
        port externalExhibitorPortal : BoothPort;
        port venueGateInterface : AccessControlPort;
        port operationsDashboard : MetricsPort;

        connect externalSubmissionPortal to paperManagement.submissions;
        connect paperManagement.schedule to programScheduling.acceptedPapers;
        connect programScheduling.programSlots to paperManagement.schedule;

        connect externalRegistrationPortal to attendeeRegistration.credentials;
        connect attendeeRegistration.credentials to accessControl.credentials;

        connect externalExhibitorPortal to exhibitorManagement.booths;

        connect venueGateInterface to accessControl.access;

        connect attendeeRegistration.metrics to analytics.registrationMetrics;
        connect exhibitorManagement.metrics to analytics.exhibitorMetrics;
        connect analytics.conferenceMetrics to operationsDashboard;

        perform action registerAttendee : RegisterAttendee;
        perform action reviewPaper : ReviewPaper;
        perform action scheduleAcceptedPaper : ScheduleAcceptedPaper;
        perform action assignExhibitorBooth : AssignExhibitorBooth;
        perform action validateAccess : ValidateAccess;

        exhibit state lifecycle : ConferenceLifecycle;
    }

    requirement def PrimaryFunctionRequirement {
        subject system : DesignAutomationConferenceAutomationSystem;
        require constraint {
            system.primaryFunction ==
            "Coordinate the Design Automation Conference by automating submission review, technical program scheduling, attendee registration, exhibitor logistics, access control, and operational reporting."
        }
    }

    requirement def CapacityRequirement {
        subject system : DesignAutomationConferenceAutomationSystem;
        require constraint {
            system.attendeeRegistration.registrationCapacity >= system.plannedAttendance and
            system.programScheduling.totalRooms >= 40 and
            system.exhibitorManagement.availableBooths >= system.plannedExhibitorBooths
        }
    }

    requirement def AccessControlRequirement {
        subject system : DesignAutomationConferenceAutomationSystem;
        require constraint {
            system.accessControl.entryGateCount >= 20 and
            system.accessControl.scanLatencyTarget <= 0.05
        }
    }

    requirement def ProgramAutomationRequirement {
        subject system : DesignAutomationConferenceAutomationSystem;
        require constraint {
            system.paperManagement.maximumSubmissions >= 2000 and
            system.paperManagement.acceptedSubmissionTarget >= 400 and
            system.programScheduling.minimumSessionDuration >= 20
        }
    }

    requirement def AnalyticsRequirement {
        subject system : DesignAutomationConferenceAutomationSystem;
        require constraint {
            system.analytics.reportingInterval <= 5
        }
    }

    part dacAutomationSystem : DesignAutomationConferenceAutomationSystem;
}

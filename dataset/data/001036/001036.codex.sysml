package ElectromechanicalFilmModel {

  import ScalarValues::*;
  import SI::*;

  attribute def Voltage_V :> Real {
    attribute unit = "V";
  }

  attribute def Current_A :> Real {
    attribute unit = "A";
  }

  attribute def Force_N :> Real {
    attribute unit = "N";
  }

  attribute def Displacement_m :> Real {
    attribute unit = "m";
  }

  attribute def Thickness_m :> Real {
    attribute unit = "m";
  }

  attribute def Capacitance_F :> Real {
    attribute unit = "F";
  }

  attribute def Temperature_C :> Real {
    attribute unit = "degC";
  }

  attribute def Pressure_Pa :> Real {
    attribute unit = "Pa";
  }

  attribute def Frequency_Hz :> Real {
    attribute unit = "Hz";
  }

  item def ElectricalDriveCommand {
    attribute requestedVoltage : Voltage_V;
    attribute rampRate : Voltage_V;
    attribute excitationFrequency : Frequency_Hz;
  }

  item def MechanicalMotion {
    attribute stroke : Displacement_m;
    attribute generatedForce : Force_N;
    attribute responseFrequency : Frequency_Hz;
  }

  item def FilmHealthStatus {
    attribute dielectricIntegrity : Real;
    attribute electrodeContinuity : Real;
    attribute measuredTemperature : Temperature_C;
    attribute leakageCurrent : Current_A;
  }

  item def ThermalLoad {
    attribute filmTemperature : Temperature_C;
    attribute ambientTemperature : Temperature_C;
  }

  item def MechanicalLoad {
    attribute appliedPressure : Pressure_Pa;
    attribute externalForce : Force_N;
  }

  port def ElectricalInputPort {
    in item command : ElectricalDriveCommand;
    out item health : FilmHealthStatus;
  }

  port def MechanicalOutputPort {
    out item motion : MechanicalMotion;
    in item load : MechanicalLoad;
  }

  port def ThermalPort {
    inout item heat : ThermalLoad;
  }

  part def HighVoltageDriver {
    attribute maximumVoltage : Voltage_V = 3000.0;
    attribute maximumCurrent : Current_A = 0.005;
    attribute switchingFrequency : Frequency_Hz = 10000.0;

    port controlInput : ElectricalInputPort;
    port filmOutput : ElectricalInputPort;

    action def ConditionDriveSignal {
      in item requested : ElectricalDriveCommand;
      out item conditioned : ElectricalDriveCommand;

      constraint {
        conditioned.requestedVoltage <= maximumVoltage
      }
    }
  }

  part def CompliantElectrode {
    attribute sheetResistance : Real;
    attribute maximumStrain : Real = 0.35;
    attribute continuityMargin : Real;

    port electricalFace : ElectricalInputPort;
  }

  part def DielectricElastomerFilm {
    attribute thickness : Thickness_m = 0.00005;
    attribute activeArea : Real = 0.01;
    attribute relativePermittivity : Real = 4.7;
    attribute capacitance : Capacitance_F = 0.000000008;
    attribute dielectricStrength : Voltage_V = 4500.0;
    attribute elasticModulus : Pressure_Pa = 1200000.0;
    attribute maximumOperatingTemperature : Temperature_C = 80.0;

    part upperElectrode : CompliantElectrode;
    part lowerElectrode : CompliantElectrode;

    port electricalPort : ElectricalInputPort;
    port mechanicalPort : MechanicalOutputPort;
    port thermalPort : ThermalPort;

    action def ConvertElectricalEnergyToFilmStrain {
      in item drive : ElectricalDriveCommand;
      in item load : MechanicalLoad;
      out item motion : MechanicalMotion;
      out item health : FilmHealthStatus;

      constraint {
        drive.requestedVoltage < dielectricStrength
      }

      constraint {
        motion.stroke >= 0.0
      }

      constraint {
        health.measuredTemperature <= maximumOperatingTemperature
      }
    }

    state def FilmOperatingState {
      state Idle;
      state Charging;
      state Deforming;
      state HoldingStroke;
      state Discharging;
      state Faulted;

      transition initial then Idle;

      transition Idle_to_Charging
        first Idle
        accept ElectricalDriveCommand
        then Charging;

      transition Charging_to_Deforming
        first Charging
        if command.requestedVoltage > 0.0
        then Deforming;

      transition Deforming_to_HoldingStroke
        first Deforming
        if motion.stroke > 0.0001
        then HoldingStroke;

      transition HoldingStroke_to_Discharging
        first HoldingStroke
        if command.requestedVoltage == 0.0
        then Discharging;

      transition Discharging_to_Idle
        first Discharging
        if health.leakageCurrent < 0.000001
        then Idle;

      transition Any_to_Faulted
        first Idle, Charging, Deforming, HoldingStroke, Discharging
        if health.measuredTemperature > maximumOperatingTemperature or
           command.requestedVoltage >= dielectricStrength
        then Faulted;
    }
  }

  part def MotionInterface {
    attribute mechanicalGain : Real = 1.0;
    attribute preloadForce : Force_N = 2.0;
    attribute maximumStroke : Displacement_m = 0.005;

    port filmSide : MechanicalOutputPort;
    port usefulOutput : MechanicalOutputPort;

    action def TransferFilmMotion {
      in item filmMotion : MechanicalMotion;
      out item outputMotion : MechanicalMotion;

      constraint {
        outputMotion.stroke <= maximumStroke
      }
    }
  }

  part def ThermalManagementLayer {
    attribute thermalResistance : Real = 12.0;
    attribute maximumAllowedTemperature : Temperature_C = 75.0;

    port filmThermalPort : ThermalPort;
    port environmentPort : ThermalPort;

    action def RejectHeat {
      inout item heatFlow : ThermalLoad;

      constraint {
        heatFlow.filmTemperature <= maximumAllowedTemperature
      }
    }
  }

  part def HealthMonitor {
    attribute leakageLimit : Current_A = 0.00001;
    attribute minimumIntegrity : Real = 0.85;

    port sensePort : ElectricalInputPort;
    port reportPort : ElectricalInputPort;

    action def EvaluateFilmHealth {
      in item status : FilmHealthStatus;
      out item safeToOperate : Boolean;

      constraint {
        safeToOperate == (
          status.leakageCurrent <= leakageLimit and
          status.dielectricIntegrity >= minimumIntegrity and
          status.electrodeContinuity >= minimumIntegrity
        )
      }
    }
  }

  part def ElectromechanicalFilmActuatorSystem {
    attribute nominalInputVoltage : Voltage_V = 1500.0;
    attribute nominalStroke : Displacement_m = 0.0015;
    attribute nominalBlockingForce : Force_N = 5.0;
    attribute nominalOperatingFrequency : Frequency_Hz = 20.0;

    part driver : HighVoltageDriver;
    part film : DielectricElastomerFilm;
    part interface : MotionInterface;
    part thermalManager : ThermalManagementLayer;
    part monitor : HealthMonitor;

    port commandPort : ElectricalInputPort;
    port outputPort : MechanicalOutputPort;
    port ambientThermalPort : ThermalPort;

    connect commandPort to driver.controlInput;
    connect driver.filmOutput to film.electricalPort;
    connect film.mechanicalPort to interface.filmSide;
    connect interface.usefulOutput to outputPort;
    connect film.thermalPort to thermalManager.filmThermalPort;
    connect thermalManager.environmentPort to ambientThermalPort;
    connect film.electricalPort to monitor.sensePort;

    action def PrimaryFunction {
      in item electricalCommand : ElectricalDriveCommand;
      in item externalLoad : MechanicalLoad;
      out item usefulMotion : MechanicalMotion;
      out item status : FilmHealthStatus;

      perform driver.ConditionDriveSignal;
      perform film.ConvertElectricalEnergyToFilmStrain;
      perform interface.TransferFilmMotion;
      perform thermalManager.RejectHeat;
      perform monitor.EvaluateFilmHealth;
    }
  }

  requirement def PrimaryFunctionRequirement {
    subject system : ElectromechanicalFilmActuatorSystem;

    require constraint {
      system.nominalInputVoltage > 0.0 and
      system.nominalStroke > 0.0 and
      system.nominalBlockingForce > 0.0
    }
  }

  requirement def ElectricalSafetyRequirement {
    subject film : DielectricElastomerFilm;

    require constraint {
      film.dielectricStrength > 1.5 * 3000.0
    }
  }

  requirement def MotionOutputRequirement {
    subject system : ElectromechanicalFilmActuatorSystem;

    require constraint {
      system.nominalStroke >= 0.001 and
      system.nominalBlockingForce >= 3.0
    }
  }

  requirement def ThermalProtectionRequirement {
    subject thermalManager : ThermalManagementLayer;

    require constraint {
      thermalManager.maximumAllowedTemperature <= 75.0
    }
  }

  requirement def HealthMonitoringRequirement {
    subject monitor : HealthMonitor;

    require constraint {
      monitor.leakageLimit <= 0.00001 and
      monitor.minimumIntegrity >= 0.85
    }
  }

  satisfy PrimaryFunctionRequirement by ElectromechanicalFilmActuatorSystem;
  satisfy ElectricalSafetyRequirement by DielectricElastomerFilm;
  satisfy MotionOutputRequirement by ElectromechanicalFilmActuatorSystem;
  satisfy ThermalProtectionRequirement by ThermalManagementLayer;
  satisfy HealthMonitoringRequirement by HealthMonitor;
}

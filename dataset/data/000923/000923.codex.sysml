package PulsometerPumpingSubsystem {
    import ScalarValues::*;
    import ISQ::*;
    import SI::*;

    attribute def Pressure :> Real {
        unit = "Pa";
    }

    attribute def FlowRate :> Real {
        unit = "m^3/s";
    }

    attribute def Volume :> Real {
        unit = "m^3";
    }

    attribute def Temperature :> Real {
        unit = "K";
    }

    attribute def Duration :> Real {
        unit = "s";
    }

    attribute def Power :> Real {
        unit = "W";
    }

    attribute def Frequency :> Real {
        unit = "Hz";
    }

    attribute def Fraction :> Real {
        unit = "1";
    }

    item def WorkingFluid {
        attribute density : Real = 998.0;
        attribute dynamicViscosity : Real = 0.001;
        attribute vaporPressure : Pressure = 3169.0;
        attribute temperature : Temperature;
        attribute suspendedSolidsFraction : Fraction;
    }

    item def Steam {
        attribute supplyPressure : Pressure;
        attribute temperature : Temperature;
        attribute quality : Fraction;
        attribute massFlowRate : Real;
    }

    item def ExhaustSteam {
        attribute pressure : Pressure;
        attribute condensateFraction : Fraction;
        attribute temperature : Temperature;
    }

    item def PumpedFluid {
        attribute pressure : Pressure;
        attribute flowRate : FlowRate;
        attribute volume : Volume;
        attribute temperature : Temperature;
    }

    item def Condensate {
        attribute pressure : Pressure;
        attribute flowRate : FlowRate;
        attribute temperature : Temperature;
    }

    port def FluidPort {
        inout item fluid : PumpedFluid;
        attribute portPressure : Pressure;
        attribute portFlowRate : FlowRate;
    }

    port def SteamInletPort {
        in item steam : Steam;
        attribute portPressure : Pressure;
        attribute portMassFlowRate : Real;
    }

    port def ExhaustPort {
        out item exhaust : ExhaustSteam;
        out item condensate : Condensate;
        attribute portPressure : Pressure;
    }

    port def VentPort {
        out item vapor : ExhaustSteam;
        attribute ventPressure : Pressure;
    }

    port def SignalPort {
        inout attribute signal : Real;
    }

    port def PowerPort {
        in attribute electricalPower : Power;
        attribute voltage : Real;
        attribute current : Real;
    }

    enum def PumpOperatingState {
        enum idle;
        enum fillingLeft;
        enum dischargingLeft;
        enum fillingRight;
        enum dischargingRight;
        enum priming;
        enum faulted;
        enum shutdown;
    }

    enum def ValvePosition {
        enum open;
        enum closed;
        enum modulating;
    }

    enum def FaultCode {
        enum none;
        enum lowSteamPressure;
        enum highDischargePressure;
        enum lowSuctionHead;
        enum chamberFlooded;
        enum valveLeakage;
        enum overTemperature;
        enum instrumentationFailure;
    }

    part def CheckValve {
        port upstream : FluidPort;
        port downstream : FluidPort;

        attribute crackingPressure : Pressure = 1500.0;
        attribute reverseLeakageRate : FlowRate = 0.000001;
        attribute position : ValvePosition;
        attribute pressureDrop : Pressure;

        action def OpenWhenForwardBiased {
            in attribute upstreamPressure : Pressure;
            in attribute downstreamPressure : Pressure;
            out attribute commandedPosition : ValvePosition;

            assert constraint {
                upstreamPressure - downstreamPressure >= crackingPressure
            }

            commandedPosition = ValvePosition::open;
        }

        action def CloseOnReverseFlow {
            in attribute upstreamPressure : Pressure;
            in attribute downstreamPressure : Pressure;
            out attribute commandedPosition : ValvePosition;

            assert constraint {
                downstreamPressure >= upstreamPressure
            }

            commandedPosition = ValvePosition::closed;
        }
    }

    part def SteamAdmissionValve {
        port steamSupply : SteamInletPort;
        port chamberSteam : SteamInletPort;
        port command : SignalPort;

        attribute position : ValvePosition;
        attribute openingFraction : Fraction;
        attribute maximumSteamMassFlowRate : Real = 0.12;
        attribute minimumSupplyPressure : Pressure = 250000.0;

        action def ModulateSteamAdmission {
            in attribute demand : Fraction;
            in attribute supplyPressure : Pressure;
            out attribute opening : Fraction;

            opening = demand;

            assert constraint {
                supplyPressure >= minimumSupplyPressure
            }
        }
    }

    part def SniftingValve {
        port chamber : ExhaustPort;
        port vent : VentPort;

        attribute position : ValvePosition;
        attribute openingPressure : Pressure = 105000.0;
        attribute closingPressure : Pressure = 101000.0;

        action def AdmitAirOrVentVapor {
            in attribute chamberPressure : Pressure;
            out attribute commandedPosition : ValvePosition;

            if chamberPressure < closingPressure {
                commandedPosition = ValvePosition::open;
            } else if chamberPressure > openingPressure {
                commandedPosition = ValvePosition::closed;
            } else {
                commandedPosition = position;
            }
        }
    }

    part def PulsometerChamber {
        port suction : FluidPort;
        port discharge : FluidPort;
        port steamIn : SteamInletPort;
        port exhaustOut : ExhaustPort;
        port vent : VentPort;

        part suctionCheckValve : CheckValve;
        part dischargeCheckValve : CheckValve;
        part steamValve : SteamAdmissionValve;
        part sniftingValve : SniftingValve;

        attribute internalVolume : Volume = 0.045;
        attribute maximumWorkingPressure : Pressure = 700000.0;
        attribute minimumSuctionPressure : Pressure = 90000.0;
        attribute nominalStrokeVolume : Volume = 0.036;
        attribute chamberPressure : Pressure;
        attribute containedFluidVolume : Volume;
        attribute cyclePeriod : Duration = 3.2;
        attribute fillingDuration : Duration = 1.8;
        attribute dischargeDuration : Duration = 1.4;
        attribute condensateVolumePerCycle : Volume = 0.0012;
        attribute isFlooded : Boolean;
        attribute isPrimed : Boolean;

        connect suction to suctionCheckValve.upstream;
        connect suctionCheckValve.downstream to dischargeCheckValve.upstream;
        connect dischargeCheckValve.downstream to discharge;
        connect steamIn to steamValve.steamSupply;
        connect steamValve.chamberSteam to steamIn;
        connect exhaustOut to sniftingValve.chamber;
        connect sniftingValve.vent to vent;

        state def ChamberCycle {
            state empty;
            state filling;
            state sealed;
            state discharging;
            state condensing;
            state venting;
            state chamberFault;

            entry action empty {
                containedFluidVolume = 0.0;
                isPrimed = false;
            }

            transition empty_to_filling
                first empty
                then filling
                accept when suction.portPressure >= minimumSuctionPressure;

            entry action filling {
                steamValve.position = ValvePosition::closed;
                suctionCheckValve.position = ValvePosition::open;
                dischargeCheckValve.position = ValvePosition::closed;
            }

            transition filling_to_sealed
                first filling
                then sealed
                accept after fillingDuration
                if containedFluidVolume >= nominalStrokeVolume;

            entry action sealed {
                suctionCheckValve.position = ValvePosition::closed;
                dischargeCheckValve.position = ValvePosition::closed;
            }

            transition sealed_to_discharging
                first sealed
                then discharging
                accept when steamIn.portPressure > discharge.portPressure + 50000.0;

            entry action discharging {
                steamValve.position = ValvePosition::open;
                suctionCheckValve.position = ValvePosition::closed;
                dischargeCheckValve.position = ValvePosition::open;
            }

            transition discharging_to_condensing
                first discharging
                then condensing
                accept after dischargeDuration
                if containedFluidVolume <= condensateVolumePerCycle;

            entry action condensing {
                steamValve.position = ValvePosition::closed;
                dischargeCheckValve.position = ValvePosition::closed;
                chamberPressure = suction.portPressure - 12000.0;
            }

            transition condensing_to_filling
                first condensing
                then filling
                accept when chamberPressure < suction.portPressure;

            transition condensing_to_venting
                first condensing
                then venting
                accept when chamberPressure > maximumWorkingPressure;

            entry action venting {
                sniftingValve.position = ValvePosition::open;
            }

            transition venting_to_filling
                first venting
                then filling
                accept when chamberPressure <= suction.portPressure;

            transition any_to_fault
                first empty, filling, sealed, discharging, condensing, venting
                then chamberFault
                accept when chamberPressure > maximumWorkingPressure or isFlooded == true;

            entry action chamberFault {
                steamValve.position = ValvePosition::closed;
                suctionCheckValve.position = ValvePosition::closed;
                dischargeCheckValve.position = ValvePosition::closed;
                sniftingValve.position = ValvePosition::open;
            }
        }
    }

    part def PulsometerPump {
        port suctionInlet : FluidPort;
        port dischargeOutlet : FluidPort;
        port steamSupply : SteamInletPort;
        port exhaust : ExhaustPort;
        port vent : VentPort;
        port control : SignalPort;

        part leftChamber : PulsometerChamber {
            attribute internalVolume = 0.045;
            attribute nominalStrokeVolume = 0.036;
        }

        part rightChamber : PulsometerChamber {
            attribute internalVolume = 0.045;
            attribute nominalStrokeVolume = 0.036;
        }

        attribute nominalFlowRate : FlowRate = 0.0225;
        attribute minimumFlowRate : FlowRate = 0.012;
        attribute maximumFlowRate : FlowRate = 0.032;
        attribute ratedDischargePressure : Pressure = 450000.0;
        attribute maximumDischargePressure : Pressure = 650000.0;
        attribute minimumSteamSupplyPressure : Pressure = 250000.0;
        attribute nominalSteamSupplyPressure : Pressure = 400000.0;
        attribute cycleFrequency : Frequency = 0.3125;
        attribute volumetricEfficiency : Fraction = 0.82;
        attribute steamConsumptionPerCubicMeter : Real = 18.0;
        attribute operatingState : PumpOperatingState;
        attribute activeFault : FaultCode;

        connect suctionInlet to leftChamber.suction;
        connect suctionInlet to rightChamber.suction;
        connect leftChamber.discharge to dischargeOutlet;
        connect rightChamber.discharge to dischargeOutlet;
        connect steamSupply to leftChamber.steamIn;
        connect steamSupply to rightChamber.steamIn;
        connect leftChamber.exhaustOut to exhaust;
        connect rightChamber.exhaustOut to exhaust;
        connect leftChamber.vent to vent;
        connect rightChamber.vent to vent;

        action def CalculateDeliveredFlow {
            in attribute strokeVolume : Volume;
            in attribute cycleRate : Frequency;
            in attribute efficiency : Fraction;
            out attribute deliveredFlow : FlowRate;

            deliveredFlow = strokeVolume * cycleRate * 2.0 * efficiency;
        }

        action def AlternateChambers {
            in attribute currentState : PumpOperatingState;
            out attribute nextState : PumpOperatingState;

            if currentState == PumpOperatingState::fillingLeft {
                nextState = PumpOperatingState::dischargingLeft;
            } else if currentState == PumpOperatingState::dischargingLeft {
                nextState = PumpOperatingState::fillingRight;
            } else if currentState == PumpOperatingState::fillingRight {
                nextState = PumpOperatingState::dischargingRight;
            } else if currentState == PumpOperatingState::dischargingRight {
                nextState = PumpOperatingState::fillingLeft;
            } else {
                nextState = PumpOperatingState::priming;
            }
        }

        state def PumpOperation {
            state idle;
            state priming;
            state fillingLeft;
            state dischargingLeft;
            state fillingRight;
            state dischargingRight;
            state faulted;
            state shutdown;

            entry action idle {
                operatingState = PumpOperatingState::idle;
                activeFault = FaultCode::none;
            }

            transition start_priming
                first idle
                then priming
                accept when control.signal > 0.5 and steamSupply.portPressure >= minimumSteamSupplyPressure;

            entry action priming {
                operatingState = PumpOperatingState::priming;
                leftChamber.steamValve.position = ValvePosition::closed;
                rightChamber.steamValve.position = ValvePosition::closed;
                leftChamber.sniftingValve.position = ValvePosition::open;
                rightChamber.sniftingValve.position = ValvePosition::open;
            }

            transition primed_to_left_fill
                first priming
                then fillingLeft
                accept when leftChamber.isPrimed == true and rightChamber.isPrimed == true;

            entry action fillingLeft {
                operatingState = PumpOperatingState::fillingLeft;
                leftChamber.suctionCheckValve.position = ValvePosition::open;
                leftChamber.dischargeCheckValve.position = ValvePosition::closed;
                rightChamber.suctionCheckValve.position = ValvePosition::closed;
            }

            transition left_fill_to_left_discharge
                first fillingLeft
                then dischargingLeft
                accept after leftChamber.fillingDuration;

            entry action dischargingLeft {
                operatingState = PumpOperatingState::dischargingLeft;
                leftChamber.steamValve.position = ValvePosition::open;
                leftChamber.dischargeCheckValve.position = ValvePosition::open;
                rightChamber.steamValve.position = ValvePosition::closed;
            }

            transition left_discharge_to_right_fill
                first dischargingLeft
                then fillingRight
                accept after leftChamber.dischargeDuration;

            entry action fillingRight {
                operatingState = PumpOperatingState::fillingRight;
                rightChamber.suctionCheckValve.position = ValvePosition::open;
                rightChamber.dischargeCheckValve.position = ValvePosition::closed;
                leftChamber.suctionCheckValve.position = ValvePosition::closed;
            }

            transition right_fill_to_right_discharge
                first fillingRight
                then dischargingRight
                accept after rightChamber.fillingDuration;

            entry action dischargingRight {
                operatingState = PumpOperatingState::dischargingRight;
                rightChamber.steamValve.position = ValvePosition::open;
                rightChamber.dischargeCheckValve.position = ValvePosition::open;
                leftChamber.steamValve.position = ValvePosition::closed;
            }

            transition right_discharge_to_left_fill
                first dischargingRight
                then fillingLeft
                accept after rightChamber.dischargeDuration;

            transition any_to_fault
                first idle, priming, fillingLeft, dischargingLeft, fillingRight, dischargingRight
                then faulted
                accept when steamSupply.portPressure < minimumSteamSupplyPressure
                    or dischargeOutlet.portPressure > maximumDischargePressure
                    or suctionInlet.portPressure < leftChamber.minimumSuctionPressure;

            entry action faulted {
                operatingState = PumpOperatingState::faulted;
                leftChamber.steamValve.position = ValvePosition::closed;
                rightChamber.steamValve.position = ValvePosition::closed;
                leftChamber.dischargeCheckValve.position = ValvePosition::closed;
                rightChamber.dischargeCheckValve.position = ValvePosition::closed;

                if steamSupply.portPressure < minimumSteamSupplyPressure {
                    activeFault = FaultCode::lowSteamPressure;
                } else if dischargeOutlet.portPressure > maximumDischargePressure {
                    activeFault = FaultCode::highDischargePressure;
                } else {
                    activeFault = FaultCode::lowSuctionHead;
                }
            }

            transition reset_from_fault
                first faulted
                then idle
                accept when control.signal == 0.0;

            transition stop_commanded
                first fillingLeft, dischargingLeft, fillingRight, dischargingRight, priming
                then shutdown
                accept when control.signal < 0.1;

            entry action shutdown {
                operatingState = PumpOperatingState::shutdown;
                leftChamber.steamValve.position = ValvePosition::closed;
                rightChamber.steamValve.position = ValvePosition::closed;
            }

            transition shutdown_to_idle
                first shutdown
                then idle
                accept after 10.0;
        }
    }

    part def SuctionStrainer {
        port inlet : FluidPort;
        port outlet : FluidPort;

        attribute meshOpening : Real = 0.003;
        attribute cleanPressureDrop : Pressure = 3000.0;
        attribute fouledPressureDrop : Pressure = 25000.0;
        attribute blockageFraction : Fraction;
        attribute allowableSolidsFraction : Fraction = 0.05;

        connect inlet to outlet;

        action def EstimatePressureDrop {
            in attribute flow : FlowRate;
            in attribute blockage : Fraction;
            out attribute pressureDrop : Pressure;

            pressureDrop = cleanPressureDrop + blockage * (fouledPressureDrop - cleanPressureDrop);
        }
    }

    part def SuctionManifold {
        port sourceConnection : FluidPort;
        port pumpConnection : FluidPort;
        port drainConnection : FluidPort;

        attribute manifoldVolume : Volume = 0.018;
        attribute designPressure : Pressure = 300000.0;
        attribute minimumNetPositiveSuctionHeadPressure : Pressure = 12000.0;

        connect sourceConnection to pumpConnection;
    }

    part def DischargeManifold {
        port pumpConnection : FluidPort;
        port deliveryConnection : FluidPort;
        port reliefConnection : FluidPort;

        attribute manifoldVolume : Volume = 0.021;
        attribute designPressure : Pressure = 750000.0;
        attribute nominalPressureDrop : Pressure = 6000.0;

        connect pumpConnection to deliveryConnection;
    }

    part def ReliefValve {
        port protectedSide : FluidPort;
        port returnSide : FluidPort;

        attribute setPressure : Pressure = 620000.0;
        attribute reseatPressure : Pressure = 540000.0;
        attribute ratedReliefFlow : FlowRate = 0.04;
        attribute position : ValvePosition;

        action def ProtectDischargeHeader {
            in attribute protectedPressure : Pressure;
            out attribute commandedPosition : ValvePosition;

            if protectedPressure >= setPressure {
                commandedPosition = ValvePosition::open;
            } else if protectedPressure <= reseatPressure {
                commandedPosition = ValvePosition::closed;
            } else {
                commandedPosition = position;
            }
        }
    }

    part def SteamSeparatorTrap {
        port steamInlet : SteamInletPort;
        port drySteamOutlet : SteamInletPort;
        port condensateOutlet : ExhaustPort;

        attribute separationEfficiency : Fraction = 0.97;
        attribute maximumCondensateFlow : FlowRate = 0.002;
        attribute minimumOutletQuality : Fraction = 0.95;

        connect steamInlet to drySteamOutlet;
    }

    part def InstrumentationSkid {
        port suctionPressureSignal : SignalPort;
        port dischargePressureSignal : SignalPort;
        port steamPressureSignal : SignalPort;
        port flowSignal : SignalPort;
        port commandSignal : SignalPort;
        port power : PowerPort;

        attribute measuredSuctionPressure : Pressure;
        attribute measuredDischargePressure : Pressure;
        attribute measuredSteamPressure : Pressure;
        attribute measuredFlowRate : FlowRate;
        attribute samplePeriod : Duration = 0.5;
        attribute controlPower : Power = 45.0;
        attribute lowSuctionAlarmPressure : Pressure = 95000.0;
        attribute highDischargeAlarmPressure : Pressure = 600000.0;
        attribute lowSteamAlarmPressure : Pressure = 240000.0;

        action def GenerateRunCommand {
            in attribute operatorDemand : Fraction;
            in attribute suctionPressure : Pressure;
            in attribute dischargePressure : Pressure;
            in attribute steamPressure : Pressure;
            out attribute command : Real;

            if suctionPressure > lowSuctionAlarmPressure
                and dischargePressure < highDischargeAlarmPressure
                and steamPressure > lowSteamAlarmPressure {
                command = operatorDemand;
            } else {
                command = 0.0;
            }
        }
    }

    part def PulsometerPumpingSubsystem {
        port fluidSource : FluidPort;
        port fluidDelivery : FluidPort;
        port steamHeader : SteamInletPort;
        port exhaustHeader : ExhaustPort;
        port ventOutlet : VentPort;
        port electricalSupply : PowerPort;
        port operatorCommand : SignalPort;

        part suctionManifold : SuctionManifold;
        part suctionStrainer : SuctionStrainer;
        part pulsometerPump : PulsometerPump;
        part dischargeManifold : DischargeManifold;
        part dischargeReliefValve : ReliefValve;
        part steamSeparatorTrap : SteamSeparatorTrap;
        part instrumentation : InstrumentationSkid;

        attribute subsystemNominalFlowRate : FlowRate = 0.0225;
        attribute subsystemMinimumFlowRate : FlowRate = 0.012;
        attribute subsystemMaximumFlowRate : FlowRate = 0.032;
        attribute subsystemRatedDischargePressure : Pressure = 450000.0;
        attribute subsystemMaximumAllowablePressure : Pressure = 750000.0;
        attribute subsystemMinimumSuctionPressure : Pressure = 90000.0;
        attribute subsystemNominalSteamPressure : Pressure = 400000.0;
        attribute subsystemMaximumSteamPressure : Pressure = 700000.0;
        attribute subsystemAvailability : Fraction = 0.98;
        attribute installedFluidVolume : Volume = 0.129;

        connect fluidSource to suctionManifold.sourceConnection;
        connect suctionManifold.pumpConnection to suctionStrainer.inlet;
        connect suctionStrainer.outlet to pulsometerPump.suctionInlet;
        connect pulsometerPump.dischargeOutlet to dischargeManifold.pumpConnection;
        connect dischargeManifold.deliveryConnection to fluidDelivery;
        connect dischargeManifold.reliefConnection to dischargeReliefValve.protectedSide;
        connect dischargeReliefValve.returnSide to suctionManifold.drainConnection;

        connect steamHeader to steamSeparatorTrap.steamInlet;
        connect steamSeparatorTrap.drySteamOutlet to pulsometerPump.steamSupply;
        connect pulsometerPump.exhaust to exhaustHeader;
        connect pulsometerPump.vent to ventOutlet;

        connect electricalSupply to instrumentation.power;
        connect operatorCommand to instrumentation.commandSignal;
        connect instrumentation.commandSignal to pulsometerPump.control;

        requirement def MoveFluidRequirement {
            subject subsystem : PulsometerPumpingSubsystem;

            require constraint {
                subsystem.pulsometerPump.nominalFlowRate >= subsystem.subsystemNominalFlowRate
            }

            require constraint {
                subsystem.fluidDelivery.portPressure >= subsystem.subsystemRatedDischargePressure
            }
        }

        requirement def PulsometerPumpRequirement {
            subject pump : PulsometerPump;

            require constraint {
                pump.leftChamber.internalVolume > pump.leftChamber.nominalStrokeVolume
                    and pump.rightChamber.internalVolume > pump.rightChamber.nominalStrokeVolume
            }

            require constraint {
                pump.cycleFrequency >= 0.2 and pump.cycleFrequency <= 0.5
            }

            require constraint {
                pump.volumetricEfficiency >= 0.75
            }
        }

        requirement def SteamSupplyRequirement {
            subject subsystem : PulsometerPumpingSubsystem;

            require constraint {
                subsystem.steamHeader.portPressure >= subsystem.pulsometerPump.minimumSteamSupplyPressure
                    and subsystem.steamHeader.portPressure <= subsystem.subsystemMaximumSteamPressure
            }

            require constraint {
                subsystem.steamSeparatorTrap.minimumOutletQuality >= 0.95
            }
        }

        requirement def PressureProtectionRequirement {
            subject subsystem : PulsometerPumpingSubsystem;

            require constraint {
                subsystem.dischargeReliefValve.setPressure < subsystem.subsystemMaximumAllowablePressure
            }

            require constraint {
                subsystem.pulsometerPump.maximumDischargePressure < subsystem.subsystemMaximumAllowablePressure
            }
        }

        requirement def SuctionProtectionRequirement {
            subject subsystem : PulsometerPumpingSubsystem;

            require constraint {
                subsystem.suctionStrainer.fouledPressureDrop <= 25000.0
            }

            require constraint {
                subsystem.fluidSource.portPressure >= subsystem.subsystemMinimumSuctionPressure
            }
        }

        requirement def AlternatingChamberRequirement {
            subject pump : PulsometerPump;

            require constraint {
                pump.leftChamber.nominalStrokeVolume == pump.rightChamber.nominalStrokeVolume
            }

            require constraint {
                pump.leftChamber.cyclePeriod == pump.rightChamber.cyclePeriod
            }
        }

        requirement def ShutdownRequirement {
            subject pump : PulsometerPump;

            require constraint {
                pump.activeFault != FaultCode::none implies pump.operatingState == PumpOperatingState::faulted
            }
        }
    }

    allocation def PumpedFluidPath {
        end source : SuctionManifold;
        end pump : PulsometerPump;
        end delivery : DischargeManifold;
    }

    allocation def SteamEnergyPath {
        end separator : SteamSeparatorTrap;
        end pump : PulsometerPump;
        end exhaust : ExhaustPort;
    }

    satisfy PulsometerPumpingSubsystem by PulsometerPumpingSubsystem::MoveFluidRequirement;
    satisfy PulsometerPumpingSubsystem.pulsometerPump by PulsometerPumpingSubsystem::PulsometerPumpRequirement;
    satisfy PulsometerPumpingSubsystem by PulsometerPumpingSubsystem::SteamSupplyRequirement;
    satisfy PulsometerPumpingSubsystem by PulsometerPumpingSubsystem::PressureProtectionRequirement;
    satisfy PulsometerPumpingSubsystem by PulsometerPumpingSubsystem::SuctionProtectionRequirement;
    satisfy PulsometerPumpingSubsystem.pulsometerPump by PulsometerPumpingSubsystem::AlternatingChamberRequirement;
    satisfy PulsometerPumpingSubsystem.pulsometerPump by PulsometerPumpingSubsystem::ShutdownRequirement;
}

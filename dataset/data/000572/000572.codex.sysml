package ConvatecInspiredWoundCareSystem {

  import ScalarValues::*;

  attribute def Pressure_kPa {
    attribute value : Real;
    attribute unit : String = "kPa";
  }

  attribute def FlowRate_mL_per_hr {
    attribute value : Real;
    attribute unit : String = "mL/h";
  }

  attribute def Volume_mL {
    attribute value : Real;
    attribute unit : String = "mL";
  }

  attribute def Time_hr {
    attribute value : Real;
    attribute unit : String = "h";
  }

  attribute def BatteryEnergy_Wh {
    attribute value : Real;
    attribute unit : String = "Wh";
  }

  attribute def SealIntegrity_percent {
    attribute value : Real;
    attribute unit : "%";
  }

  item def WoundExudate {
    attribute volume : Volume_mL;
    attribute estimatedFlowRate : FlowRate_mL_per_hr;
  }

  item def FilteredAir {
    attribute odorReduced : Boolean;
  }

  item def TherapyCommand {
    attribute targetPressure : Pressure_kPa;
    attribute therapyDuration : Time_hr;
  }

  item def AlarmSignal {
    attribute alarmCode : String;
    attribute priority : String;
  }

  port def ExudatePort {
    out item exudate : WoundExudate;
  }

  port def SuctionPort {
    in item exudate : WoundExudate;
    out item filteredAir : FilteredAir;
  }

  port def ControlPort {
    in item command : TherapyCommand;
    out item alarm : AlarmSignal;
  }

  requirement def PrimaryFunctionRequirement {
    doc /* The system shall provide high-level wound exudate management by maintaining a sealed dressing interface, applying controlled negative pressure, collecting exudate, filtering vented air, and alerting the user when therapy cannot be maintained. */
  }

  requirement def PressureControlRequirement {
    attribute nominalTarget : Pressure_kPa = (value = -12.5, unit = "kPa");
    attribute tolerance : Pressure_kPa = (value = 1.5, unit = "kPa");
    doc /* The therapy pump shall regulate dressing pressure within tolerance of the commanded target pressure during active therapy. */
  }

  requirement def CollectionRequirement {
    attribute minimumCanisterCapacity : Volume_mL = (value = 300.0, unit = "mL");
    doc /* The exudate canister shall retain collected wound fluid without backflow during normal patient mobility. */
  }

  requirement def AlarmRequirement {
    doc /* The controller shall issue an alarm for leak, blockage, full canister, low battery, or pump fault conditions. */
  }

  action def ApplyNegativePressure {
    in command : TherapyCommand;
    out deliveredPressure : Pressure_kPa;
  }

  action def CollectExudate {
    in incomingExudate : WoundExudate;
    out storedVolume : Volume_mL;
  }

  action def MonitorTherapy {
    in measuredPressure : Pressure_kPa;
    in sealIntegrity : SealIntegrity_percent;
    in canisterVolume : Volume_mL;
    in batteryEnergy : BatteryEnergy_Wh;
    out alarm : AlarmSignal;
  }

  state def TherapyOperatingStates {
    state Standby;
    state SealCheck;
    state ActiveTherapy;
    state Alarmed;
    state Paused;
    state Shutdown;

    transition first Standby;
    transition Standby then SealCheck;
    transition SealCheck then ActiveTherapy;
    transition ActiveTherapy then Alarmed;
    transition Alarmed then Paused;
    transition Paused then SealCheck;
    transition ActiveTherapy then Shutdown;
    transition Standby then Shutdown;
  }

  part def HydrocolloidDressing {
    attribute contactArea_cm2 : Real;
    attribute sealIntegrity : SealIntegrity_percent;
    port woundInterface : ExudatePort;
    port suctionInterface : SuctionPort;
  }

  part def NegativePressurePump {
    attribute maximumVacuum : Pressure_kPa = (value = -25.0, unit = "kPa");
    attribute nominalFlowRate : FlowRate_mL_per_hr = (value = 80.0, unit = "mL/h");
    port inlet : SuctionPort;
    perform action ApplyNegativePressure;
  }

  part def ExudateCanister {
    attribute capacity : Volume_mL = (value = 300.0, unit = "mL");
    attribute currentFill : Volume_mL = (value = 0.0, unit = "mL");
    port inlet : SuctionPort;
    perform action CollectExudate;
  }

  part def OdorAndBacterialFilter {
    attribute bacterialEfficiency_percent : Real = 99.9;
    port inlet : SuctionPort;
    port outlet : SuctionPort;
  }

  part def TherapyController {
    attribute commandedPressure : Pressure_kPa = (value = -12.5, unit = "kPa");
    attribute sessionDuration : Time_hr = (value = 8.0, unit = "h");
    port clinicianInterface : ControlPort;
    perform action MonitorTherapy;
    exhibit state TherapyOperatingStates;
  }

  part def RechargeablePowerPack {
    attribute storedEnergy : BatteryEnergy_Wh = (value = 24.0, unit = "Wh");
    attribute lowEnergyThreshold : BatteryEnergy_Wh = (value = 3.0, unit = "Wh");
  }

  part def ConvatecInspiredTherapyUnit {
    satisfy PrimaryFunctionRequirement;
    satisfy PressureControlRequirement;
    satisfy CollectionRequirement;
    satisfy AlarmRequirement;

    attribute primaryFunction : String =
      "Maintain a protected wound environment while removing exudate through controlled negative pressure therapy.";

    part dressing : HydrocolloidDressing;
    part pump : NegativePressurePump;
    part canister : ExudateCanister;
    part filter : OdorAndBacterialFilter;
    part controller : TherapyController;
    part powerPack : RechargeablePowerPack;

    port woundDrain : ExudatePort;
    port userControl : ControlPort;

    connect woundDrain to dressing.woundInterface;
    connect dressing.suctionInterface to pump.inlet;
    connect pump.inlet to canister.inlet;
    connect canister.inlet to filter.inlet;
    connect controller.clinicianInterface to userControl;
  }

}

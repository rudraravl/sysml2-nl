package SpecificSpeedPumpModel {

  import ScalarValues::*;
  import SI::*;
  import ISQ::*;

  attribute def SpecificSpeed :> Real {
    doc /* Dimensionless normalized turbomachine parameter used to select pump geometry and operating envelope. */
  }

  attribute def VolumeFlowRate :> Real {
    unit = "m^3/s";
  }

  attribute def RotationalSpeed :> Real {
    unit = "rpm";
  }

  attribute def HydraulicHead :> Real {
    unit = "m";
  }

  attribute def Pressure :> Real {
    unit = "Pa";
  }

  attribute def Power :> Real {
    unit = "W";
  }

  attribute def Efficiency :> Real {
    unit = "1";
  }

  attribute def Temperature :> Real {
    unit = "K";
  }

  item def Water {
    attribute density : Real = 997.0;
    attribute temperature : Temperature;
  }

  item def ElectricalPower {
    attribute voltage : Real;
    attribute current : Real;
    attribute frequency : Real;
  }

  item def SpeedCommand {
    attribute targetSpeed : RotationalSpeed;
  }

  item def FlowCommand {
    attribute targetFlow : VolumeFlowRate;
  }

  item def PumpStatus {
    attribute measuredFlow : VolumeFlowRate;
    attribute measuredHead : HydraulicHead;
    attribute measuredSpeed : RotationalSpeed;
    attribute measuredPower : Power;
    attribute operatingEfficiency : Efficiency;
    attribute alarmActive : Boolean;
  }

  port def FluidInletPort {
    in item incomingFluid : Water;
    attribute inletPressure : Pressure;
  }

  port def FluidOutletPort {
    out item dischargedFluid : Water;
    attribute outletPressure : Pressure;
  }

  port def PowerInputPort {
    in item suppliedPower : ElectricalPower;
  }

  port def CommandInputPort {
    in item flowCommand : FlowCommand;
    in item speedCommand : SpeedCommand;
  }

  port def StatusOutputPort {
    out item status : PumpStatus;
  }

  part def Impeller {
    attribute designSpecificSpeed : SpecificSpeed;
    attribute diameter : Real;
    attribute bladeCount : Integer;
    attribute rotationalSpeed : RotationalSpeed;
    attribute generatedHead : HydraulicHead;

    port inlet : FluidInletPort;
    port outlet : FluidOutletPort;
  }

  part def ElectricMotor {
    attribute ratedPower : Power;
    attribute ratedSpeed : RotationalSpeed;
    attribute shaftSpeed : RotationalSpeed;

    port powerIn : PowerInputPort;
    port speedCommandIn : CommandInputPort;
  }

  part def VariableFrequencyDrive {
    attribute outputFrequency : Real;
    attribute commandedSpeed : RotationalSpeed;

    port powerIn : PowerInputPort;
    port commandIn : CommandInputPort;
    port motorPowerOut : PowerInputPort;
  }

  part def PumpCasing {
    attribute maximumPressure : Pressure;
    attribute hydraulicLossCoefficient : Real;

    port suction : FluidInletPort;
    port discharge : FluidOutletPort;
  }

  part def FlowSensor {
    attribute measuredFlow : VolumeFlowRate;

    port sensedFluid : FluidOutletPort;
    port statusOut : StatusOutputPort;
  }

  part def PressureSensor {
    attribute measuredPressure : Pressure;

    port sensedFluid : FluidOutletPort;
    port statusOut : StatusOutputPort;
  }

  part def PumpController {
    attribute requestedFlow : VolumeFlowRate;
    attribute computedSpecificSpeed : SpecificSpeed;
    attribute selectedSpeed : RotationalSpeed;
    attribute minimumAllowedEfficiency : Efficiency = 0.72;

    port commandIn : CommandInputPort;
    port statusOut : StatusOutputPort;
    port driveCommandOut : CommandInputPort;
  }

  action def ComputeSpecificSpeed {
    in flow : VolumeFlowRate;
    in speed : RotationalSpeed;
    in head : HydraulicHead;
    out specificSpeed : SpecificSpeed;

    constraint specificSpeedEquation {
      specificSpeed == speed * sqrt(flow) / pow(head, 0.75)
    }
  }

  action def RegulateBySpecificSpeed {
    in targetFlow : VolumeFlowRate;
    in measuredFlow : VolumeFlowRate;
    in measuredHead : HydraulicHead;
    in designSpecificSpeed : SpecificSpeed;
    out commandedSpeed : RotationalSpeed;

    action estimateRequiredSpeed;
    action compareSpecificSpeed;
    action limitMotorSpeed;
    action issueSpeedCommand;

    first estimateRequiredSpeed
      then compareSpecificSpeed
      then limitMotorSpeed
      then issueSpeedCommand;
  }

  state def PumpOperatingState {
    state Off;
    state Priming;
    state Accelerating;
    state RunningAtDesignSpecificSpeed;
    state CorrectingSpeed;
    state Faulted;
    state Shutdown;

    transition startPump
      first Off
      then Priming;

    transition primeComplete
      first Priming
      then Accelerating;

    transition designSpeedReached
      first Accelerating
      then RunningAtDesignSpecificSpeed;

    transition flowDeviationDetected
      first RunningAtDesignSpecificSpeed
      then CorrectingSpeed;

    transition speedCorrected
      first CorrectingSpeed
      then RunningAtDesignSpecificSpeed;

    transition faultDetected
      first RunningAtDesignSpecificSpeed
      then Faulted;

    transition commandedStop
      first RunningAtDesignSpecificSpeed
      then Shutdown;

    transition resetComplete
      first Faulted
      then Off;

    transition shutdownComplete
      first Shutdown
      then Off;
  }

  part def SpecificSpeedBasedPumpSystem {
    doc /* Primary function: move water from a low-pressure inlet to a higher-pressure outlet while regulating impeller speed so operation remains near the selected design specific speed. */

    attribute designSpecificSpeed : SpecificSpeed = 38.0;
    attribute nominalFlow : VolumeFlowRate = 0.085;
    attribute nominalHead : HydraulicHead = 42.0;
    attribute nominalSpeed : RotationalSpeed = 1780.0;
    attribute nominalEfficiency : Efficiency = 0.81;
    attribute ratedHydraulicPower : Power = 35000.0;

    port waterIn : FluidInletPort;
    port waterOut : FluidOutletPort;
    port electricalInput : PowerInputPort;
    port operatorCommand : CommandInputPort;
    port systemStatus : StatusOutputPort;

    part casing : PumpCasing {
      attribute maximumPressure = 650000.0;
      attribute hydraulicLossCoefficient = 0.08;
    }

    part impeller : Impeller {
      attribute designSpecificSpeed = 38.0;
      attribute diameter = 0.315;
      attribute bladeCount = 6;
      attribute rotationalSpeed = 1780.0;
      attribute generatedHead = 42.0;
    }

    part motor : ElectricMotor {
      attribute ratedPower = 45000.0;
      attribute ratedSpeed = 1800.0;
      attribute shaftSpeed = 1780.0;
    }

    part drive : VariableFrequencyDrive {
      attribute outputFrequency = 59.3;
      attribute commandedSpeed = 1780.0;
    }

    part controller : PumpController {
      attribute requestedFlow = 0.085;
      attribute computedSpecificSpeed = 38.0;
      attribute selectedSpeed = 1780.0;
    }

    part flowSensor : FlowSensor;
    part dischargePressureSensor : PressureSensor;

    connect waterIn to casing.suction;
    connect casing.discharge to impeller.inlet;
    connect impeller.outlet to waterOut;

    connect electricalInput to drive.powerIn;
    connect drive.motorPowerOut to motor.powerIn;
    connect operatorCommand to controller.commandIn;
    connect controller.driveCommandOut to drive.commandIn;
    connect flowSensor.statusOut to controller.statusOut;
    connect dischargePressureSensor.statusOut to controller.statusOut;
    connect controller.statusOut to systemStatus;

    perform action computeDesignSpecificSpeed : ComputeSpecificSpeed {
      in flow = nominalFlow;
      in speed = nominalSpeed;
      in head = nominalHead;
      out specificSpeed = designSpecificSpeed;
    }

    perform action closedLoopRegulation : RegulateBySpecificSpeed {
      in targetFlow = nominalFlow;
      in measuredFlow = flowSensor.measuredFlow;
      in measuredHead = impeller.generatedHead;
      in designSpecificSpeed = designSpecificSpeed;
      out commandedSpeed = drive.commandedSpeed;
    }

    exhibit state pumpState : PumpOperatingState;
  }

  requirement def PrimaryFunctionRequirement {
    subject pumpSystem : SpecificSpeedBasedPumpSystem;

    require constraint {
      pumpSystem.waterOut.outletPressure > pumpSystem.waterIn.inletPressure
    }

    doc /* The system shall increase water pressure and deliver commanded flow while operating near the selected design specific speed. */
  }

  requirement def SpecificSpeedRequirement {
    subject pumpSystem : SpecificSpeedBasedPumpSystem;

    require constraint {
      pumpSystem.designSpecificSpeed >= 32.0 and pumpSystem.designSpecificSpeed <= 44.0
    }

    doc /* The pump shall be designed for a mixed-flow specific speed range suitable for moderate head and moderate flow service. */
  }

  requirement def NominalFlowRequirement {
    subject pumpSystem : SpecificSpeedBasedPumpSystem;

    require constraint {
      pumpSystem.nominalFlow >= 0.080 and pumpSystem.nominalFlow <= 0.090
    }

    doc /* The system shall provide nominal water flow of 0.085 m^3/s within allowed tolerance. */
  }

  requirement def NominalHeadRequirement {
    subject pumpSystem : SpecificSpeedBasedPumpSystem;

    require constraint {
      pumpSystem.nominalHead >= 40.0 and pumpSystem.nominalHead <= 44.0
    }

    doc /* The system shall generate nominal hydraulic head of approximately 42 m. */
  }

  requirement def EfficiencyRequirement {
    subject pumpSystem : SpecificSpeedBasedPumpSystem;

    require constraint {
      pumpSystem.nominalEfficiency >= 0.78
    }

    doc /* The system shall maintain hydraulic efficiency of at least 78 percent at the design operating point. */
  }

  requirement def ElectricalPowerRequirement {
    subject pumpSystem : SpecificSpeedBasedPumpSystem;

    require constraint {
      pumpSystem.ratedHydraulicPower <= pumpSystem.motor.ratedPower
    }

    doc /* The motor and drive shall provide sufficient electrical power for the required hydraulic output. */
  }

  part specificSpeedPumpInstallation : SpecificSpeedBasedPumpSystem;

  satisfy PrimaryFunctionRequirement by specificSpeedPumpInstallation;
  satisfy SpecificSpeedRequirement by specificSpeedPumpInstallation;
  satisfy NominalFlowRequirement by specificSpeedPumpInstallation;
  satisfy NominalHeadRequirement by specificSpeedPumpInstallation;
  satisfy EfficiencyRequirement by specificSpeedPumpInstallation;
  satisfy ElectricalPowerRequirement by specificSpeedPumpInstallation;
}

package StrainRateImagingSystemModel {

  import ScalarValues::*;
  import ISQ::*;
  import SI::*;

  attribute def Frequency :> Real {
    unit = "Hz";
  }

  attribute def FrameRate :> Real {
    unit = "frame/s";
  }

  attribute def Distance :> Real {
    unit = "m";
  }

  attribute def Velocity :> Real {
    unit = "m/s";
  }

  attribute def Strain :> Real {
    unit = "1";
  }

  attribute def StrainRate :> Real {
    unit = "1/s";
  }

  attribute def Pressure :> Real {
    unit = "Pa";
  }

  attribute def Voltage :> Real {
    unit = "V";
  }

  attribute def Power :> Real {
    unit = "W";
  }

  attribute def Temperature :> Real {
    unit = "degC";
  }

  item def AcousticPulse {
    attribute centerFrequency : Frequency;
    attribute pulsePressure : Pressure;
    attribute pulseDuration : Real;
    attribute steeringAngle : Real;
  }

  item def EchoSignal {
    attribute receiveFrequency : Frequency;
    attribute amplitude : Voltage;
    attribute timeOfFlight : Real;
    attribute channelIndex : Integer;
  }

  item def RFFrame {
    attribute frameId : Integer;
    attribute frameRate : FrameRate;
    attribute sampleDepth : Distance;
    attribute lineCount : Integer;
  }

  item def BModeFrame {
    attribute frameId : Integer;
    attribute pixelWidth : Integer;
    attribute pixelHeight : Integer;
    attribute dynamicRange : Real;
  }

  item def TissueMotionVector {
    attribute axialVelocity : Velocity;
    attribute lateralVelocity : Velocity;
    attribute trackingConfidence : Real;
  }

  item def StrainRateMap {
    attribute peakSystolicRate : StrainRate;
    attribute peakDiastolicRate : StrainRate;
    attribute spatialResolution : Distance;
    attribute temporalResolution : Real;
  }

  item def DiagnosticReport {
    attribute globalLongitudinalStrain : Strain;
    attribute maxStrainRate : StrainRate;
    attribute minStrainRate : StrainRate;
    attribute imageQualityIndex : Real;
  }

  port def AcousticTransmitPort {
    out item pulse : AcousticPulse;
  }

  port def AcousticReceivePort {
    in item echo : EchoSignal;
  }

  port def RFDataPort {
    out item rfFrame : RFFrame;
  }

  port def ImageFramePort {
    out item imageFrame : BModeFrame;
  }

  port def MotionDataPort {
    out item motion : TissueMotionVector;
  }

  port def StrainRateMapPort {
    out item map : StrainRateMap;
  }

  port def ReportPort {
    out item report : DiagnosticReport;
  }

  port def PowerPort {
    in item supplyVoltage : Voltage;
    in item supplyPower : Power;
  }

  part def UltrasoundTransducerArray {
    attribute elementCount : Integer = 128;
    attribute centerFrequency : Frequency = 2500000.0;
    attribute apertureWidth : Distance = 0.038;
    attribute surfaceTemperature : Temperature;

    port powerIn : PowerPort;
    port acousticOut : AcousticTransmitPort;
    port echoIn : AcousticReceivePort;
  }

  part def Beamformer {
    attribute transmitFocusDepth : Distance = 0.08;
    attribute receiveApertureElements : Integer = 64;
    attribute steeringAngleLimit : Real = 30.0;

    port echoIn : AcousticReceivePort;
    port rfOut : RFDataPort;
  }

  part def RFSignalProcessor {
    attribute samplingFrequency : Frequency = 40000000.0;
    attribute wallFilterCutoff : Frequency = 80.0;
    attribute gain : Real = 42.0;

    port rfIn : RFDataPort;
    port imageOut : ImageFramePort;
  }

  part def TissueMotionEstimator {
    attribute minimumTrackingConfidence : Real = 0.75;
    attribute kernelSizeAxial : Distance = 0.004;
    attribute kernelSizeLateral : Distance = 0.006;

    port imageIn : ImageFramePort;
    port motionOut : MotionDataPort;
  }

  part def StrainRateCalculator {
    attribute spatialGradientWindow : Distance = 0.008;
    attribute maxValidStrainRate : StrainRate = 8.0;
    attribute minValidStrainRate : StrainRate = -8.0;

    port motionIn : MotionDataPort;
    port strainRateOut : StrainRateMapPort;
  }

  part def VisualizationAndReportingConsole {
    attribute displayWidthPixels : Integer = 1920;
    attribute displayHeightPixels : Integer = 1080;
    attribute reportRetentionDays : Integer = 365;

    port imageIn : ImageFramePort;
    port strainRateIn : StrainRateMapPort;
    port reportOut : ReportPort;
  }

  part def PatientInterface {
    attribute targetAnatomy : String = "myocardial tissue";
    attribute acousticCouplingQuality : Real;
  }

  part def StrainRateImagingSystem {
    attribute primaryFunction : String =
      "Acquire ultrasound echo data from deforming biological tissue, estimate tissue motion over time, compute spatial velocity gradients, and present strain rate images that quantify local tissue deformation.";

    part patient : PatientInterface;
    part transducer : UltrasoundTransducerArray;
    part beamformer : Beamformer;
    part rfProcessor : RFSignalProcessor;
    part motionEstimator : TissueMotionEstimator;
    part strainRateCalculator : StrainRateCalculator;
    part console : VisualizationAndReportingConsole;

    connect transducer.echoIn to beamformer.echoIn;
    connect beamformer.rfOut to rfProcessor.rfIn;
    connect rfProcessor.imageOut to motionEstimator.imageIn;
    connect rfProcessor.imageOut to console.imageIn;
    connect motionEstimator.motionOut to strainRateCalculator.motionIn;
    connect strainRateCalculator.strainRateOut to console.strainRateIn;

    action acquireAndAnalyzeTissueDeformation {
      first startExam;
      then transmitUltrasoundPulse;
      then receiveEchoSignals;
      then reconstructRFFrame;
      then formBModeImage;
      then estimateTissueMotion;
      then computeStrainRateMap;
      then renderDiagnosticDisplay;
      then generateReport;

      action startExam {
        out targetDepth : Distance = 0.12;
        out requiredFrameRate : FrameRate = 80.0;
      }

      action transmitUltrasoundPulse {
        in targetDepth : Distance;
        out pulse : AcousticPulse;
      }

      action receiveEchoSignals {
        in pulse : AcousticPulse;
        out echo : EchoSignal;
      }

      action reconstructRFFrame {
        in echo : EchoSignal;
        out rfFrame : RFFrame;
      }

      action formBModeImage {
        in rfFrame : RFFrame;
        out imageFrame : BModeFrame;
      }

      action estimateTissueMotion {
        in imageFrame : BModeFrame;
        out motion : TissueMotionVector;
      }

      action computeStrainRateMap {
        in motion : TissueMotionVector;
        out strainRateMap : StrainRateMap;
      }

      action renderDiagnosticDisplay {
        in imageFrame : BModeFrame;
        in strainRateMap : StrainRateMap;
      }

      action generateReport {
        in strainRateMap : StrainRateMap;
        out report : DiagnosticReport;
      }
    }

    state machine operationalStates {
      state Off;
      state Initializing;
      state ProbeReady;
      state Imaging;
      state Processing;
      state DisplayingResults;
      state Fault;

      initial then Off;

      transition powerOn
        first Off
        then Initializing;

      transition initializationComplete
        first Initializing
        then ProbeReady;

      transition startAcquisition
        first ProbeReady
        then Imaging;

      transition frameCaptured
        first Imaging
        then Processing;

      transition mapComputed
        first Processing
        then DisplayingResults;

      transition acquireNextFrame
        first DisplayingResults
        then Imaging;

      transition stopExam
        first DisplayingResults
        then ProbeReady;

      transition unsafeTemperature
        first Imaging
        then Fault;

      transition trackingFailure
        first Processing
        then Fault;

      transition resetFault
        first Fault
        then ProbeReady;
    }
  }

  requirement def PrimaryFunctionRequirement {
    doc
      "The system shall provide a high-level clinical imaging function that quantifies tissue deformation rate by acquiring ultrasound image sequences, estimating tissue motion, computing strain rate, and displaying a spatial strain rate image.";
  }

  requirement def TemporalResolutionRequirement {
    doc
      "The system shall acquire image frames at a rate sufficient to resolve cardiac tissue deformation throughout systole and diastole.";
    attribute minimumFrameRate : FrameRate = 60.0;
  }

  requirement def StrainRateComputationRequirement {
    doc
      "The system shall compute strain rate as the spatial gradient of estimated tissue velocity within a defined anatomical region of interest.";
    attribute maximumComputationLatency : Real = 0.2;
  }

  requirement def ImageQualityRequirement {
    doc
      "The system shall reject or flag strain rate results when motion tracking confidence is below the configured quality threshold.";
    attribute minimumTrackingConfidence : Real = 0.75;
  }

  requirement def PatientSafetyRequirement {
    doc
      "The system shall limit acoustic output and probe surface temperature during imaging operation.";
    attribute maximumProbeSurfaceTemperature : Temperature = 43.0;
    attribute maximumPulsePressure : Pressure = 2500000.0;
  }

  satisfy PrimaryFunctionRequirement by StrainRateImagingSystem;
  satisfy TemporalResolutionRequirement by StrainRateImagingSystem::rfProcessor;
  satisfy StrainRateComputationRequirement by StrainRateImagingSystem::strainRateCalculator;
  satisfy ImageQualityRequirement by StrainRateImagingSystem::motionEstimator;
  satisfy PatientSafetyRequirement by StrainRateImagingSystem::transducer;
}

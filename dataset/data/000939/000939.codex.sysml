package SlipFactorBasedCompressorSystem {
    import ScalarValues::*;
    import ISQ::*;
    import SI::*;

    attribute def SlipFactor : Real {
        doc "Dimensionless ratio of actual tangential exit velocity to ideal blade-speed-based tangential exit velocity.";
    }

    attribute def Efficiency : Real;
    attribute def BladeCount : Integer;
    attribute def Angle : Real;
    attribute def RotationalSpeed : Real;
    attribute def Pressure : Real;
    attribute def Temperature : Real;
    attribute def MassFlowRate : Real;
    attribute def Torque : Real;
    attribute def Power : Real;

    item def WorkingGas {
        attribute pressure : Pressure;
        attribute temperature : Temperature;
        attribute massFlow : MassFlowRate;
        attribute density : Real;
    }

    item def ShaftPower {
        attribute power : Power;
        attribute torque : Torque;
        attribute speed : RotationalSpeed;
    }

    item def SlipEstimate {
        attribute slipFactor : SlipFactor;
        attribute uncertainty : Real;
        attribute valid : Boolean;
    }

    item def ControlCommand {
        attribute speedSetpoint : RotationalSpeed;
        attribute inletGuideVaneAngle : Angle;
        attribute bleedValveOpening : Real;
    }

    item def HealthReport {
        attribute currentSlipFactor : SlipFactor;
        attribute predictedEfficiency : Efficiency;
        attribute surgeMargin : Real;
        attribute statusCode : Integer;
    }

    port def GasInletPort {
        in item gasIn : WorkingGas;
    }

    port def GasOutletPort {
        out item gasOut : WorkingGas;
    }

    port def ShaftPowerPort {
        in item shaftPower : ShaftPower;
    }

    port def CommandPort {
        in item command : ControlCommand;
    }

    port def EstimatePort {
        out item estimate : SlipEstimate;
    }

    port def ReportPort {
        out item report : HealthReport;
    }

    port def SensorPort {
        out item sensedGas : WorkingGas;
        out item sensedPower : ShaftPower;
    }

    part def SlipFactorCompressor {
        doc "A centrifugal compressor system whose primary function is to convert shaft power into gas pressure rise while estimating slip factor and regulating operating conditions to preserve pressure delivery, efficiency, and surge margin.";

        attribute designSlipFactor : SlipFactor = 0.86;
        attribute minimumAllowedSlipFactor : SlipFactor = 0.72;
        attribute maximumAllowedSlipFactor : SlipFactor = 0.94;
        attribute targetPressureRatio : Real = 2.4;
        attribute targetEfficiency : Efficiency = 0.78;
        attribute minimumSurgeMargin : Real = 0.12;

        port inlet : GasInletPort;
        port outlet : GasOutletPort;
        port shaft : ShaftPowerPort;
        port commandInput : CommandPort;
        port estimateOutput : EstimatePort;
        port reportOutput : ReportPort;

        part inletDuct : InletDuct;
        part impeller : SlipSensitiveImpeller;
        part diffuser : Diffuser;
        part volute : Volute;
        part sensorSuite : CompressorSensorSuite;
        part estimator : SlipFactorEstimator;
        part controller : SlipFactorController;
        part actuatorSet : ActuatorSet;

        connect inlet.gasIn to inletDuct.gasIn;
        connect inletDuct.gasOut to impeller.gasIn;
        connect shaft.shaftPower to impeller.shaftPower;
        connect impeller.gasOut to diffuser.gasIn;
        connect diffuser.gasOut to volute.gasIn;
        connect volute.gasOut to outlet.gasOut;

        connect sensorSuite.sensedGas to estimator.measuredGas;
        connect sensorSuite.sensedPower to estimator.measuredPower;
        connect estimator.estimate to estimateOutput.estimate;
        connect estimator.estimate to controller.slipEstimate;
        connect commandInput.command to controller.externalCommand;
        connect controller.command to actuatorSet.command;
        connect controller.report to reportOutput.report;

        perform action compressGas;
        perform action estimateSlipFactor;
        perform action regulateSlipFactor;
    }

    part def InletDuct {
        attribute pressureLoss : Pressure;
        port gasIn : GasInletPort;
        port gasOut : GasOutletPort;
    }

    part def SlipSensitiveImpeller {
        attribute bladeCount : BladeCount = 12;
        attribute exitBladeAngle : Angle = 35.0;
        attribute tipRadius : Real = 0.145;
        attribute tipClearance : Real = 0.0006;
        attribute currentSlipFactor : SlipFactor;
        attribute idealTangentialExitVelocity : Real;
        attribute actualTangentialExitVelocity : Real;

        port gasIn : GasInletPort;
        port gasOut : GasOutletPort;
        port shaftPower : ShaftPowerPort;
    }

    part def Diffuser {
        attribute staticPressureRecovery : Real = 0.63;
        attribute lossCoefficient : Real = 0.08;
        port gasIn : GasInletPort;
        port gasOut : GasOutletPort;
    }

    part def Volute {
        attribute collectionLossCoefficient : Real = 0.04;
        port gasIn : GasInletPort;
        port gasOut : GasOutletPort;
    }

    part def CompressorSensorSuite {
        port sensed : SensorPort;
        port sensedGas : SensorPort;
        port sensedPower : SensorPort;

        part inletPressureSensor : PressureSensor;
        part outletPressureSensor : PressureSensor;
        part temperatureSensor : TemperatureSensor;
        part flowMeter : MassFlowSensor;
        part shaftSpeedSensor : SpeedSensor;
        part torqueSensor : TorqueSensor;
    }

    part def PressureSensor {
        attribute rangeMinimum : Pressure = 50000.0;
        attribute rangeMaximum : Pressure = 800000.0;
        attribute accuracy : Real = 0.005;
    }

    part def TemperatureSensor {
        attribute rangeMinimum : Temperature = 220.0;
        attribute rangeMaximum : Temperature = 520.0;
        attribute accuracy : Real = 0.004;
    }

    part def MassFlowSensor {
        attribute rangeMinimum : MassFlowRate = 0.05;
        attribute rangeMaximum : MassFlowRate = 3.50;
        attribute accuracy : Real = 0.006;
    }

    part def SpeedSensor {
        attribute rangeMinimum : RotationalSpeed = 5000.0;
        attribute rangeMaximum : RotationalSpeed = 95000.0;
        attribute accuracy : Real = 0.002;
    }

    part def TorqueSensor {
        attribute rangeMinimum : Torque = 0.0;
        attribute rangeMaximum : Torque = 160.0;
        attribute accuracy : Real = 0.005;
    }

    part def SlipFactorEstimator {
        attribute estimatedSlipFactor : SlipFactor;
        attribute estimateUncertainty : Real;
        attribute samplePeriod : Real = 0.02;

        port measuredGas : SensorPort;
        port measuredPower : SensorPort;
        port estimate : EstimatePort;

        perform action computeEulerVelocityTriangle;
        perform action calculateSlipFactor;
        perform action validateEstimate;
    }

    part def SlipFactorController {
        attribute requestedPressureRatio : Real;
        attribute commandedSpeed : RotationalSpeed;
        attribute commandedVaneAngle : Angle;
        attribute commandedBleedOpening : Real;

        port slipEstimate : EstimatePort;
        port externalCommand : CommandPort;
        port command : CommandPort;
        port report : ReportPort;

        perform action compareSlipToOperatingEnvelope;
        perform action adjustSpeedAndVanes;
        perform action publishHealthReport;
    }

    part def ActuatorSet {
        port command : CommandPort;

        part variableSpeedDrive : VariableSpeedDrive;
        part inletGuideVanes : InletGuideVanes;
        part bleedValve : BleedValve;
    }

    part def VariableSpeedDrive {
        attribute maximumSpeed : RotationalSpeed = 90000.0;
        attribute minimumSpeed : RotationalSpeed = 12000.0;
        attribute speedRampLimit : Real = 3000.0;
    }

    part def InletGuideVanes {
        attribute minimumAngle : Angle = -20.0;
        attribute maximumAngle : Angle = 65.0;
        attribute currentAngle : Angle;
    }

    part def BleedValve {
        attribute openingFraction : Real;
        attribute maximumFlowFraction : Real = 0.18;
    }

    action def CompressGas {
        in item inletGas : WorkingGas;
        in item shaftInput : ShaftPower;
        out item outletGas : WorkingGas;

        objective {
            doc "Increase gas static pressure by transferring shaft power through a slip-sensitive impeller and recovering dynamic pressure in the diffuser and volute.";
        }
    }

    action def EstimateSlipFactor {
        in item measuredGas : WorkingGas;
        in item measuredPower : ShaftPower;
        out item slip : SlipEstimate;

        objective {
            doc "Calculate real-time slip factor from measured flow, pressure rise, shaft speed, torque, blade geometry, and inferred exit velocity triangle.";
        }
    }

    action def RegulateSlipFactor {
        in item slip : SlipEstimate;
        in item operatorCommand : ControlCommand;
        out item actuatorCommand : ControlCommand;

        objective {
            doc "Keep slip factor within the validated operating envelope by coordinating speed, inlet guide vane angle, and bleed valve position.";
        }
    }

    state def CompressorOperatingState {
        entry action initializeEstimator;
        state Off;
        state Startup;
        state Stabilizing;
        state NominalCompression;
        state SlipLimitedOperation;
        state SurgeAvoidance;
        state FaultShutdown;

        transition first Off;
        transition Off to Startup
            accept StartCommand;

        transition Startup to Stabilizing
            if shaftSpeedAboveMinimum;

        transition Stabilizing to NominalCompression
            if pressureRatioWithinTolerance and slipFactorValid;

        transition NominalCompression to SlipLimitedOperation
            if estimatedSlipFactor < minimumAllowedSlipFactor;

        transition SlipLimitedOperation to NominalCompression
            if estimatedSlipFactor >= designSlipFactor and surgeMargin >= minimumSurgeMargin;

        transition NominalCompression to SurgeAvoidance
            if surgeMargin < minimumSurgeMargin;

        transition SurgeAvoidance to Stabilizing
            if surgeMargin >= minimumSurgeMargin;

        transition Startup to FaultShutdown
            if sensorFaultDetected;

        transition NominalCompression to FaultShutdown
            if overspeedDetected or overtemperatureDetected;

        transition SlipLimitedOperation to FaultShutdown
            if estimatedSlipFactor < 0.65;

        transition FaultShutdown to Off
            accept ResetCommand;
    }

    requirement def PrimaryFunctionRequirement {
        subject compressor : SlipFactorCompressor;

        require constraint {
            compressor.targetPressureRatio >= 2.0 and
            compressor.targetEfficiency >= 0.75
        }

        doc "The system shall convert shaft power into compressed gas flow while using slip factor as a primary performance variable for control and health assessment.";
    }

    requirement def SlipEnvelopeRequirement {
        subject compressor : SlipFactorCompressor;

        require constraint {
            compressor.minimumAllowedSlipFactor <= compressor.designSlipFactor and
            compressor.designSlipFactor <= compressor.maximumAllowedSlipFactor
        }

        doc "The system shall maintain estimated slip factor inside the calibrated operating envelope during steady compression.";
    }

    requirement def SurgeProtectionRequirement {
        subject compressor : SlipFactorCompressor;

        require constraint {
            compressor.minimumSurgeMargin >= 0.10
        }

        doc "The controller shall increase surge margin by opening bleed flow or reducing pressure ratio demand when slip degradation indicates flow separation risk.";
    }

    requirement def EstimationValidityRequirement {
        subject estimator : SlipFactorEstimator;

        require constraint {
            estimator.samplePeriod <= 0.05 and
            estimator.estimateUncertainty <= 0.03
        }

        doc "The slip factor estimator shall publish a valid estimate at least every 50 milliseconds with uncertainty no greater than 0.03 in nominal sensor conditions.";
    }

    requirement def ActuationRequirement {
        subject actuatorSet : ActuatorSet;

        require constraint {
            actuatorSet.variableSpeedDrive.maximumSpeed >= 85000.0 and
            actuatorSet.bleedValve.maximumFlowFraction >= 0.15
        }

        doc "The actuator set shall provide enough authority to recover from low-slip operation without violating overspeed or surge limits.";
    }

    satisfy PrimaryFunctionRequirement by SlipFactorCompressor;
    satisfy SlipEnvelopeRequirement by SlipFactorCompressor.controller;
    satisfy SurgeProtectionRequirement by SlipFactorCompressor.controller;
    satisfy EstimationValidityRequirement by SlipFactorCompressor.estimator;
    satisfy ActuationRequirement by SlipFactorCompressor.actuatorSet;

    part compressorSystem : SlipFactorCompressor {
        attribute designSlipFactor = 0.86;
        attribute minimumAllowedSlipFactor = 0.72;
        attribute maximumAllowedSlipFactor = 0.94;
        attribute targetPressureRatio = 2.4;
        attribute targetEfficiency = 0.78;
        attribute minimumSurgeMargin = 0.12;
    }
}

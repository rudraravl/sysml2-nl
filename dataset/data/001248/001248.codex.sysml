package ShockDetectorSystemModel {

    import ScalarValues::*;
    import SI::*;

    item def AccelerationSample {
        attribute ax : Real;
        attribute ay : Real;
        attribute az : Real;
        attribute sampleTime : Real;
    }

    item def ShockEvent {
        attribute peakAcceleration : Real;
        attribute duration : Real;
        attribute detectedTime : Real;
        attribute severity : ShockSeverity;
    }

    item def AlertMessage {
        attribute eventTime : Real;
        attribute peakAcceleration : Real;
        attribute severity : ShockSeverity;
        attribute acknowledged : Boolean;
    }

    enum def ShockSeverity {
        enum low;
        enum moderate;
        enum severe;
        enum critical;
    }

    value def Acceleration_g : Real {
        unit = "g";
    }

    value def Time_ms : Real {
        unit = "ms";
    }

    value def Frequency_Hz : Real {
        unit = "Hz";
    }

    value def Voltage_V : Real {
        unit = "V";
    }

    value def Current_mA : Real {
        unit = "mA";
    }

    value def Temperature_C : Real {
        unit = "degC";
    }

    port def AccelerationInputPort {
        in sample : AccelerationSample;
    }

    port def EventOutputPort {
        out event : ShockEvent;
    }

    port def AlertOutputPort {
        out alert : AlertMessage;
    }

    port def PowerInputPort {
        in supplyVoltage : Voltage_V;
        in supplyCurrent : Current_mA;
    }

    port def UserControlPort {
        in armCommand : Boolean;
        in resetCommand : Boolean;
        out armedStatus : Boolean;
        out faultStatus : Boolean;
    }

    part def ShockDetector {
        attribute sampleRate : Frequency_Hz = 1000.0;
        attribute warningThreshold : Acceleration_g = 5.0;
        attribute shockThreshold : Acceleration_g = 12.0;
        attribute criticalThreshold : Acceleration_g = 35.0;
        attribute minimumShockDuration : Time_ms = 2.0;
        attribute maximumOperatingTemperature : Temperature_C = 85.0;
        attribute nominalVoltage : Voltage_V = 3.3;

        port accelerationIn : AccelerationInputPort;
        port powerIn : PowerInputPort;
        port eventOut : EventOutputPort;
        port alertOut : AlertOutputPort;
        port control : UserControlPort;

        part sensor : TriAxisAccelerometer;
        part signalConditioner : SignalConditioner;
        part classifier : ShockClassifier;
        part controller : DetectorController;
        part alertInterface : AlertInterface;
        part eventMemory : EventMemory;
        part powerManager : PowerManager;

        connect accelerationIn.sample to sensor.rawSample;
        connect sensor.measuredSample to signalConditioner.inputSample;
        connect signalConditioner.filteredSample to classifier.conditionedSample;
        connect classifier.detectedEvent to controller.classifiedEvent;
        connect controller.recordedEvent to eventMemory.eventIn;
        connect controller.alertMessage to alertInterface.alertIn;
        connect controller.eventOutput to eventOut.event;
        connect alertInterface.alertOut to alertOut.alert;
        connect powerIn.supplyVoltage to powerManager.inputVoltage;
        connect powerIn.supplyCurrent to powerManager.inputCurrent;
        connect powerManager.regulatedVoltage to sensor.supplyVoltage;
        connect powerManager.regulatedVoltage to signalConditioner.supplyVoltage;
        connect powerManager.regulatedVoltage to classifier.supplyVoltage;
        connect powerManager.regulatedVoltage to controller.supplyVoltage;
        connect control.armCommand to controller.armCommand;
        connect control.resetCommand to controller.resetCommand;
        connect controller.armedStatus to control.armedStatus;
        connect controller.faultStatus to control.faultStatus;
    }

    part def TriAxisAccelerometer {
        attribute measurementRange : Acceleration_g = 100.0;
        attribute noiseDensity : Real = 0.002;
        attribute bandwidth : Frequency_Hz = 500.0;

        in rawSample : AccelerationSample;
        out measuredSample : AccelerationSample;
        in supplyVoltage : Voltage_V;

        action measureAcceleration {
            in sampleIn : AccelerationSample;
            out sampleOut : AccelerationSample;
        }
    }

    part def SignalConditioner {
        attribute lowPassCutoff : Frequency_Hz = 250.0;
        attribute highPassCutoff : Frequency_Hz = 1.0;
        attribute calibrationOffsetX : Acceleration_g = 0.0;
        attribute calibrationOffsetY : Acceleration_g = 0.0;
        attribute calibrationOffsetZ : Acceleration_g = 0.0;

        in inputSample : AccelerationSample;
        out filteredSample : AccelerationSample;
        in supplyVoltage : Voltage_V;

        action filterAndCalibrate {
            in unfiltered : AccelerationSample;
            out filtered : AccelerationSample;
        }
    }

    part def ShockClassifier {
        attribute warningThreshold : Acceleration_g = 5.0;
        attribute shockThreshold : Acceleration_g = 12.0;
        attribute criticalThreshold : Acceleration_g = 35.0;
        attribute minimumDuration : Time_ms = 2.0;

        in conditionedSample : AccelerationSample;
        out detectedEvent : ShockEvent;
        in supplyVoltage : Voltage_V;

        action computeVectorMagnitude {
            in sample : AccelerationSample;
            out magnitude : Acceleration_g;
        }

        action classifyShock {
            in peakMagnitude : Acceleration_g;
            in duration : Time_ms;
            out event : ShockEvent;
        }
    }

    part def DetectorController {
        attribute isArmed : Boolean = false;
        attribute faultPresent : Boolean = false;
        attribute lastPeakAcceleration : Acceleration_g = 0.0;
        attribute eventCounter : Integer = 0;

        in classifiedEvent : ShockEvent;
        in armCommand : Boolean;
        in resetCommand : Boolean;
        in supplyVoltage : Voltage_V;
        out recordedEvent : ShockEvent;
        out eventOutput : ShockEvent;
        out alertMessage : AlertMessage;
        out armedStatus : Boolean;
        out faultStatus : Boolean;

        state def DetectorOperatingState {
            entry action initializeDetector;

            state off;
            state selfTest;
            state disarmed;
            state armedMonitoring;
            state shockDetected;
            state fault;

            transition first off then selfTest;
            transition selfTest then disarmed if supplyVoltage >= 3.0;
            transition selfTest then fault if supplyVoltage < 3.0;
            transition disarmed then armedMonitoring if armCommand == true;
            transition armedMonitoring then disarmed if armCommand == false;
            transition armedMonitoring then shockDetected if classifiedEvent.peakAcceleration >= 12.0;
            transition shockDetected then armedMonitoring if resetCommand == true;
            transition armedMonitoring then fault if supplyVoltage < 2.9;
            transition fault then selfTest if resetCommand == true;
        }

        action processDetectedShock {
            in event : ShockEvent;
            out storedEvent : ShockEvent;
            out outboundAlert : AlertMessage;
        }
    }

    part def AlertInterface {
        attribute alertLatencyLimit : Time_ms = 50.0;

        in alertIn : AlertMessage;
        out alertOut : AlertMessage;

        action transmitAlert {
            in message : AlertMessage;
            out transmitted : AlertMessage;
        }
    }

    part def EventMemory {
        attribute capacity : Integer = 1024;
        attribute retainedEventCount : Integer = 0;

        in eventIn : ShockEvent;

        action storeEvent {
            in event : ShockEvent;
        }

        action clearEvents {
            out retainedEventCount : Integer;
        }
    }

    part def PowerManager {
        attribute minimumInputVoltage : Voltage_V = 3.0;
        attribute maximumInputVoltage : Voltage_V = 5.5;
        attribute regulatedOutputVoltage : Voltage_V = 3.3;
        attribute maximumCurrentDraw : Current_mA = 25.0;

        in inputVoltage : Voltage_V;
        in inputCurrent : Current_mA;
        out regulatedVoltage : Voltage_V;

        action regulatePower {
            in vin : Voltage_V;
            out vout : Voltage_V;
        }
    }

    part def ProtectedAsset {
        attribute assetIdentifier : String;
        attribute maximumPermittedShock : Acceleration_g = 20.0;

        port shockEventInput : EventOutputPort;
    }

    part shockDetectionSystem {
        part detector : ShockDetector;
        part protectedAsset : ProtectedAsset;

        connect detector.eventOut.event to protectedAsset.shockEventInput.event;
    }

    requirement def DetectShockRequirement {
        subject detector : ShockDetector;
        doc /* The shock detector shall detect an acceleration transient whose vector magnitude equals or exceeds 12 g for at least 2 ms. */
        require constraint {
            detector.shockThreshold == 12.0 and detector.minimumShockDuration == 2.0
        }
    }

    requirement def ClassifySeverityRequirement {
        subject detector : ShockDetector;
        doc /* The shock detector shall classify detected shock events as low, moderate, severe, or critical according to measured peak acceleration. */
        require constraint {
            detector.warningThreshold < detector.shockThreshold and detector.shockThreshold < detector.criticalThreshold
        }
    }

    requirement def AlertRequirement {
        subject detector : ShockDetector;
        doc /* The shock detector shall issue an alert message for each detected shock event within 50 ms of event confirmation. */
        require constraint {
            detector.alertInterface.alertLatencyLimit <= 50.0
        }
    }

    requirement def RecordEventRequirement {
        subject detector : ShockDetector;
        doc /* The shock detector shall record the peak acceleration, duration, severity, and detection time for each confirmed shock event. */
        require constraint {
            detector.eventMemory.capacity >= 1024
        }
    }

    requirement def PowerRequirement {
        subject detector : ShockDetector;
        doc /* The shock detector shall operate from a regulated 3.3 V supply with maximum current draw not exceeding 25 mA. */
        require constraint {
            detector.powerManager.regulatedOutputVoltage == 3.3 and detector.powerManager.maximumCurrentDraw <= 25.0
        }
    }

    requirement def PrimaryFunctionRequirement {
        subject detector : ShockDetector;
        doc /* The primary function of the shock detector is to monitor tri-axis acceleration, identify high-magnitude transient shocks, classify their severity, store the event record, and notify external systems. */
    }

    satisfy DetectShockRequirement by shockDetectionSystem.detector.classifier;
    satisfy ClassifySeverityRequirement by shockDetectionSystem.detector.classifier;
    satisfy AlertRequirement by shockDetectionSystem.detector.alertInterface;
    satisfy RecordEventRequirement by shockDetectionSystem.detector.eventMemory;
    satisfy PowerRequirement by shockDetectionSystem.detector.powerManager;
    satisfy PrimaryFunctionRequirement by shockDetectionSystem.detector;
}

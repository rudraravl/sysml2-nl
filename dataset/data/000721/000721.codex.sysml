package OstomySystemModel {

    import ScalarValues::*;
    import ISQ::*;
    import SI::*;

    attribute def MassPerArea {
        :> ScalarValues::Real;
        unit = "g/m^2";
    }

    attribute def FlowRate {
        :> ScalarValues::Real;
        unit = "mL/h";
    }

    attribute def Volume {
        :> ScalarValues::Real;
        unit = "mL";
    }

    attribute def Pressure {
        :> ScalarValues::Real;
        unit = "kPa";
    }

    attribute def TimeDuration {
        :> ScalarValues::Real;
        unit = "h";
    }

    attribute def SkinAdhesionStrength {
        :> ScalarValues::Real;
        unit = "N/25mm";
    }

    attribute def OdorPermeability {
        :> ScalarValues::Real;
        unit = "relative_index";
    }

    attribute def pHValue {
        :> ScalarValues::Real;
        unit = "pH";
    }

    enum def EffluentConsistency {
        enum watery;
        enum liquid;
        enum semiFormed;
        enum formed;
    }

    enum def PouchFillLevel {
        enum empty;
        enum low;
        enum moderate;
        enum high;
        enum full;
    }

    enum def SealIntegrity {
        enum intact;
        enum compromised;
        enum failed;
    }

    enum def UserAction {
        enum applySystem;
        enum inspectSeal;
        enum emptyPouch;
        enum replacePouch;
        enum replaceBarrier;
        enum cleanSkin;
        enum disposeWaste;
    }

    item def StomalEffluent {
        attribute volume : Volume;
        attribute flowRate : FlowRate;
        attribute consistency : EffluentConsistency;
        attribute pH : pHValue;
        attribute gasVolume : Volume;
    }

    item def IntestinalGas {
        attribute volume : Volume;
        attribute odorLoad : ScalarValues::Real;
        attribute pressureContribution : Pressure;
    }

    item def FilteredGas {
        attribute volume : Volume;
        attribute residualOdorLoad : ScalarValues::Real;
    }

    item def UsedDrainage {
        attribute liquidVolume : Volume;
        attribute solidFraction : ScalarValues::Real;
        attribute odorLoad : ScalarValues::Real;
    }

    item def SkinMoisture {
        attribute moistureMassPerArea : MassPerArea;
        attribute pH : pHValue;
    }

    item def UserCommand {
        attribute requestedAction : UserAction;
    }

    port def StomaInterfacePort {
        in item effluentIn : StomalEffluent;
        in item gasIn : IntestinalGas;
    }

    port def SkinInterfacePort {
        inout item moisture : SkinMoisture;
        out item adhesionStatus : SealIntegrity;
    }

    port def EffluentTransferPort {
        inout item effluent : StomalEffluent;
        inout item gas : IntestinalGas;
    }

    port def GasVentPort {
        in item rawGas : IntestinalGas;
        out item filteredGas : FilteredGas;
    }

    port def DrainPort {
        out item usedDrainage : UsedDrainage;
        in item drainCommand : UserCommand;
    }

    port def UserInterfacePort {
        in item userCommand : UserCommand;
        out item fillLevelIndication : PouchFillLevel;
        out item sealIndication : SealIntegrity;
    }

    part def Stoma {
        attribute nominalEffluentFlow : FlowRate = 45.0;
        attribute peakEffluentFlow : FlowRate = 180.0;
        attribute nominalGasFlow : FlowRate = 20.0;

        port output : StomaInterfacePort;
    }

    part def PeristomalSkin {
        attribute acceptableMoistureLimit : MassPerArea = 15.0;
        attribute irritationRiskIndex : ScalarValues::Real;
        attribute surfacePrepared : ScalarValues::Boolean;

        port skinSurface : SkinInterfacePort;
    }

    part def SkinBarrier {
        attribute hydrocolloidThickness : LengthValue = 1.2 [mm];
        attribute adhesiveStrength : SkinAdhesionStrength = 10.0;
        attribute wearTimeRemaining : TimeDuration = 72.0;
        attribute sealState : SealIntegrity = SealIntegrity::intact;
        attribute openingDiameter : LengthValue = 30.0 [mm];
        attribute maxOpeningDiameter : LengthValue = 45.0 [mm];

        port stomaSide : EffluentTransferPort;
        port skinSide : SkinInterfacePort;
        port pouchSide : EffluentTransferPort;
    }

    part def CouplingRing {
        attribute locked : ScalarValues::Boolean = true;
        attribute ringDiameter : LengthValue = 57.0 [mm];
        attribute leakPressureThreshold : Pressure = 4.0;

        port barrierSide : EffluentTransferPort;
        port pouchSide : EffluentTransferPort;
    }

    part def CollectionPouch {
        attribute capacity : Volume = 650.0;
        attribute currentVolume : Volume = 0.0;
        attribute fillLevel : PouchFillLevel = PouchFillLevel::empty;
        attribute internalPressure : Pressure = 0.0;
        attribute filmOdorBarrierIndex : ScalarValues::Real = 0.98;
        attribute outletClosed : ScalarValues::Boolean = true;

        port inlet : EffluentTransferPort;
        port vent : GasVentPort;
        port outlet : DrainPort;
        port userInterface : UserInterfacePort;
    }

    part def OdorFilter {
        attribute activatedCarbonMass : MassValue = 1.5 [g];
        attribute odorPermeability : OdorPermeability = 0.05;
        attribute cloggingIndex : ScalarValues::Real = 0.0;
        attribute ventingPressureLimit : Pressure = 2.0;

        port inlet : GasVentPort;
        port ambientOutlet : GasVentPort;
    }

    part def DrainableClosure {
        attribute clampEngaged : ScalarValues::Boolean = true;
        attribute foldCount : ScalarValues::Integer = 3;
        attribute maxDrainRate : FlowRate = 900.0;

        port pouchOutlet : DrainPort;
        port disposalOutlet : DrainPort;
    }

    part def DisposalContainer {
        attribute availableCapacity : Volume = 2000.0;
        attribute sealedAfterUse : ScalarValues::Boolean = false;

        port input : DrainPort;
    }

    part def OstomySystem {
        attribute primaryFunction : ScalarValues::String =
            "Collect, contain, vent, and enable hygienic disposal of stomal effluent while maintaining a protective seal around the stoma and supporting user-managed wear.";

        attribute targetWearDuration : TimeDuration = 72.0;
        attribute minimumUsableCapacity : Volume = 500.0;
        attribute maximumAllowedLeakRate : FlowRate = 0.5;
        attribute maximumComfortPressure : Pressure = 3.0;

        part stoma : Stoma;
        part skin : PeristomalSkin;
        part barrier : SkinBarrier;
        part coupling : CouplingRing;
        part pouch : CollectionPouch;
        part filter : OdorFilter;
        part closure : DrainableClosure;
        part disposal : DisposalContainer;

        port userAccess : UserInterfacePort;

        connect stoma.output.effluentIn to barrier.stomaSide.effluent;
        connect stoma.output.gasIn to barrier.stomaSide.gas;
        connect skin.skinSurface to barrier.skinSide;
        connect barrier.pouchSide to coupling.barrierSide;
        connect coupling.pouchSide to pouch.inlet;
        connect pouch.vent to filter.inlet;
        connect filter.ambientOutlet to pouch.vent;
        connect pouch.outlet to closure.pouchOutlet;
        connect closure.disposalOutlet to disposal.input;
        connect userAccess to pouch.userInterface;
    }

    action def CollectEffluent {
        in item incomingEffluent : StomalEffluent;
        inout item pouchContents : StomalEffluent;
        out fillLevel : PouchFillLevel;

        first start;
        then receiveEffluent;
        then updateStoredVolume;
        then classifyFillLevel;
        then done;

        action receiveEffluent;
        action updateStoredVolume;
        action classifyFillLevel;
    }

    action def VentGas {
        in item rawGas : IntestinalGas;
        out item filteredGas : FilteredGas;
        in cloggingIndex : ScalarValues::Real;
        out ventingAcceptable : ScalarValues::Boolean;

        first start;
        then passThroughFilter;
        then reduceOdorLoad;
        then evaluateBackPressure;
        then done;

        action passThroughFilter;
        action reduceOdorLoad;
        action evaluateBackPressure;
    }

    action def MaintainSkinSeal {
        in moisture : SkinMoisture;
        in adhesiveStrength : SkinAdhesionStrength;
        in wearTimeRemaining : TimeDuration;
        out sealState : SealIntegrity;

        first start;
        then assessMoisture;
        then assessAdhesion;
        then assessWearTime;
        then determineSealIntegrity;
        then done;

        action assessMoisture;
        action assessAdhesion;
        action assessWearTime;
        action determineSealIntegrity;
    }

    action def EmptyPouch {
        in command : UserCommand;
        inout pouchVolume : Volume;
        out item drainedMaterial : UsedDrainage;
        out closureSecured : ScalarValues::Boolean;

        first start;
        then openClosure;
        then drainContents;
        then cleanOutlet;
        then resealClosure;
        then verifyClosure;
        then done;

        action openClosure;
        action drainContents;
        action cleanOutlet;
        action resealClosure;
        action verifyClosure;
    }

    state def PouchUseState {
        entry action initializeVolume;
        state Empty;
        state Collecting;
        state Venting;
        state ReadyToEmpty;
        state Emptying;
        state Reclosed;
        state ReplaceRequired;

        transition first Empty;
        transition Empty to Collecting
            accept StomalEffluent
            if incomingEffluent.volume > 0.0;
        transition Collecting to Venting
            accept IntestinalGas
            if incomingGas.volume > 0.0;
        transition Venting to Collecting
            if internalPressure <= 3.0;
        transition Collecting to ReadyToEmpty
            if currentVolume >= 450.0;
        transition ReadyToEmpty to Emptying
            accept UserCommand
            if requestedAction == UserAction::emptyPouch;
        transition Emptying to Reclosed
            if currentVolume <= 50.0 and outletClosed == true;
        transition Reclosed to Collecting
            if sealState == SealIntegrity::intact;
        transition Collecting to ReplaceRequired
            if sealState == SealIntegrity::failed or currentVolume >= capacity;
        transition ReadyToEmpty to ReplaceRequired
            if sealState == SealIntegrity::failed;
    }

    state def BarrierSealState {
        state Prepared;
        state Applied;
        state Sealed;
        state AtRisk;
        state Compromised;
        state Removed;

        transition first Prepared;
        transition Prepared to Applied
            accept UserCommand
            if requestedAction == UserAction::applySystem;
        transition Applied to Sealed
            if adhesiveStrength >= 8.0 and surfacePrepared == true;
        transition Sealed to AtRisk
            if wearTimeRemaining <= 12.0 or moisture.moistureMassPerArea > 12.0;
        transition AtRisk to Compromised
            if adhesiveStrength < 6.0 or moisture.moistureMassPerArea > 15.0;
        transition Compromised to Removed
            accept UserCommand
            if requestedAction == UserAction::replaceBarrier;
        transition Removed to Prepared
            accept UserCommand
            if requestedAction == UserAction::cleanSkin;
    }

    requirement def PrimaryFunctionRequirement {
        doc /* The ostomy system shall collect and contain stomal effluent, vent intestinal gas through an odor-reducing path, protect peristomal skin through a maintained adhesive seal, and provide a controlled user-operated drainage path for disposal. */
    }

    requirement def CapacityRequirement {
        attribute requiredCapacity : Volume = 500.0;
        doc /* The collection pouch shall provide usable containment volume of at least the required capacity before replacement is required. */
    }

    requirement def SealProtectionRequirement {
        attribute minimumAdhesion : SkinAdhesionStrength = 8.0;
        attribute targetWearDuration : TimeDuration = 72.0;
        doc /* The skin barrier shall maintain an intact seal during normal use for the target wear duration when applied to prepared peristomal skin. */
    }

    requirement def OdorControlRequirement {
        attribute maximumOdorPermeability : OdorPermeability = 0.10;
        doc /* The gas vent path shall reduce odor transmission by filtering intestinal gas before release to ambient air. */
    }

    requirement def DrainageRequirement {
        attribute minimumDrainRate : FlowRate = 300.0;
        doc /* The drainable closure shall enable controlled emptying of pouch contents and shall be resealable after emptying. */
    }

    requirement def ComfortPressureRequirement {
        attribute maximumInternalPressure : Pressure = 3.0;
        doc /* The pouch and venting subsystem shall limit normal internal pressure to a level compatible with comfort and seal retention. */
    }

    requirement def SkinMoistureRequirement {
        attribute maximumMoistureAtBarrier : MassPerArea = 15.0;
        doc /* The barrier interface shall limit retained moisture at the peristomal skin interface to reduce risk of seal compromise. */
    }

    requirement def DisposalHygieneRequirement {
        doc /* The system shall support transfer of used drainage to a disposal container while minimizing direct user contact with effluent. */
    }

    satisfy PrimaryFunctionRequirement by OstomySystem;
    satisfy CapacityRequirement by CollectionPouch;
    satisfy SealProtectionRequirement by SkinBarrier;
    satisfy OdorControlRequirement by OdorFilter;
    satisfy DrainageRequirement by DrainableClosure;
    satisfy ComfortPressureRequirement by CollectionPouch;
    satisfy SkinMoistureRequirement by SkinBarrier;
    satisfy DisposalHygieneRequirement by DrainableClosure;

    assert constraint CapacityConstraint {
        CollectionPouch::capacity >= OstomySystem::minimumUsableCapacity
    }

    assert constraint PressureConstraint {
        CollectionPouch::internalPressure <= OstomySystem::maximumComfortPressure
    }

    assert constraint FilterConstraint {
        OdorFilter::odorPermeability <= 0.10
    }

    assert constraint SealConstraint {
        SkinBarrier::adhesiveStrength >= 8.0 implies SkinBarrier::sealState == SealIntegrity::intact
    }

    assert constraint DrainageConstraint {
        DrainableClosure::maxDrainRate >= 300.0
    }

}

package ProgrammableMatterSystemModel {
    import ScalarValues::*;
    import ISQ::*;
    import SI::*;

    value def Percent {
        specializes Real;
        unit = "%";
    }

    value def Millimeter {
        specializes Real;
        unit = "mm";
    }

    value def Millisecond {
        specializes Real;
        unit = "ms";
    }

    value def Celsius {
        specializes Real;
        unit = "degC";
    }

    value def Volt {
        specializes Real;
        unit = "V";
    }

    value def Ampere {
        specializes Real;
        unit = "A";
    }

    value def Newton {
        specializes Real;
        unit = "N";
    }

    value def Hertz {
        specializes Real;
        unit = "Hz";
    }

    value def Joule {
        specializes Real;
        unit = "J";
    }

    item def ShapeProgram {
        attribute programId : String;
        attribute targetShapeName : String;
        attribute voxelResolution : Millimeter;
        attribute maxTransitionTime : Millisecond;
        attribute requiredSurfaceRigidity : Newton;
    }

    item def NeighborMessage {
        attribute senderId : String;
        attribute receiverId : String;
        attribute localPositionX : Millimeter;
        attribute localPositionY : Millimeter;
        attribute localPositionZ : Millimeter;
        attribute bondRequest : Boolean;
        attribute detachRequest : Boolean;
    }

    item def PowerPacket {
        attribute voltage : Volt;
        attribute current : Ampere;
        attribute availableEnergy : Joule;
    }

    item def SensorSample {
        attribute temperature : Celsius;
        attribute strain : Newton;
        attribute contactDetected : Boolean;
        attribute neighborSignalStrength : Percent;
    }

    item def MorphologyStatus {
        attribute activeVoxelCount : Integer;
        attribute shapeCompletion : Percent;
        attribute averageTemperature : Celsius;
        attribute faultedVoxelCount : Integer;
        attribute stable : Boolean;
    }

    port def ProgramPort {
        in item program : ShapeProgram;
        out item status : MorphologyStatus;
    }

    port def PowerPort {
        in item supply : PowerPacket;
    }

    port def NeighborCoordinationPort {
        in item inbound : NeighborMessage;
        out item outbound : NeighborMessage;
    }

    port def SensorPort {
        out item sample : SensorSample;
    }

    port def ActuationPort {
        in item command : ShapeProgram;
        out item status : MorphologyStatus;
    }

    part def ProgrammableMatterVoxel {
        attribute voxelId : String;
        attribute edgeLength : Millimeter = 2.0;
        attribute maxBondForce : Newton = 1.5;
        attribute operatingTemperature : Celsius;
        attribute batteryEnergy : Joule;
        attribute isBondedNorth : Boolean;
        attribute isBondedSouth : Boolean;
        attribute isBondedEast : Boolean;
        attribute isBondedWest : Boolean;
        attribute isBondedUp : Boolean;
        attribute isBondedDown : Boolean;

        port powerPort : PowerPort;
        port northPort : NeighborCoordinationPort;
        port southPort : NeighborCoordinationPort;
        port eastPort : NeighborCoordinationPort;
        port westPort : NeighborCoordinationPort;
        port upPort : NeighborCoordinationPort;
        port downPort : NeighborCoordinationPort;
        port sensorPort : SensorPort;
        port actuationPort : ActuationPort;

        action senseLocalEnvironment {
            out item sample : SensorSample;
        }

        action evaluateBondCommand {
            in item program : ShapeProgram;
            in item neighborMessage : NeighborMessage;
            out item bondMessage : NeighborMessage;
        }

        action actuateBondingLatches {
            in item bondMessage : NeighborMessage;
            out item status : MorphologyStatus;
        }

        state def VoxelLifecycle {
            state dormant;
            state initialized;
            state locatingNeighbors;
            state bonding;
            state loadBearing;
            state detaching;
            state faulted;

            initial then dormant;

            transition dormant_to_initialized
                first dormant
                then initialized;

            transition initialized_to_locatingNeighbors
                first initialized
                then locatingNeighbors;

            transition locatingNeighbors_to_bonding
                first locatingNeighbors
                then bonding;

            transition bonding_to_loadBearing
                first bonding
                then loadBearing;

            transition loadBearing_to_detaching
                first loadBearing
                then detaching;

            transition detaching_to_locatingNeighbors
                first detaching
                then locatingNeighbors;

            transition any_to_faulted
                first initialized
                then faulted;
        }
    }

    part def DistributedMorphologyController {
        attribute controllerId : String;
        attribute controlFrequency : Hertz = 50.0;
        attribute targetCompletionThreshold : Percent = 98.0;
        attribute maximumAllowedTemperature : Celsius = 70.0;
        attribute commandedResolution : Millimeter = 2.0;

        port programPort : ProgramPort;
        port voxelCommandPort : ActuationPort;
        port voxelStatusPort : SensorPort;

        action loadShapeProgram {
            in item program : ShapeProgram;
            out item validatedProgram : ShapeProgram;
        }

        action computeVoxelAssignments {
            in item validatedProgram : ShapeProgram;
            out item voxelCommand : ShapeProgram;
        }

        action monitorMorphology {
            in item sample : SensorSample;
            out item status : MorphologyStatus;
        }

        action publishSystemStatus {
            in item status : MorphologyStatus;
            out item reportedStatus : MorphologyStatus;
        }

        state def ControllerLifecycle {
            state idle;
            state validatingProgram;
            state distributingCommands;
            state supervisingMorph;
            state verifyingShape;
            state maintainingShape;
            state emergencyStop;

            initial then idle;

            transition idle_to_validatingProgram
                first idle
                then validatingProgram;

            transition validatingProgram_to_distributingCommands
                first validatingProgram
                then distributingCommands;

            transition distributingCommands_to_supervisingMorph
                first distributingCommands
                then supervisingMorph;

            transition supervisingMorph_to_verifyingShape
                first supervisingMorph
                then verifyingShape;

            transition verifyingShape_to_maintainingShape
                first verifyingShape
                then maintainingShape;

            transition maintainingShape_to_supervisingMorph
                first maintainingShape
                then supervisingMorph;

            transition supervisingMorph_to_emergencyStop
                first supervisingMorph
                then emergencyStop;
        }
    }

    part def EnergyDistributionMesh {
        attribute nominalVoltage : Volt = 12.0;
        attribute maximumCurrent : Ampere = 20.0;
        attribute storedEnergy : Joule = 50000.0;
        attribute minimumReserveEnergy : Joule = 5000.0;

        port inputPower : PowerPort;
        port distributedPower : PowerPort;

        action regulateVoltage {
            in item input : PowerPacket;
            out item regulated : PowerPacket;
        }

        action isolateFaultedBranch {
            in item status : MorphologyStatus;
            out item regulated : PowerPacket;
        }
    }

    part def ProgrammableMatterAssembly {
        attribute systemId : String = "PM-Shape-Adaptive-Material-01";
        attribute primaryFunction : String = "Reconfigure a lattice of addressable matter voxels into commanded three-dimensional shapes while maintaining structural integrity, power continuity, and distributed coordination.";
        attribute maximumShapeTransitionTime : Millisecond = 10000.0;
        attribute nominalVoxelEdgeLength : Millimeter = 2.0;
        attribute maximumSurfaceLoad : Newton = 120.0;
        attribute maximumOperatingTemperature : Celsius = 65.0;

        port userProgramPort : ProgramPort;
        port externalPowerPort : PowerPort;
        port systemStatusPort : ProgramPort;

        part controller : DistributedMorphologyController;
        part energyMesh : EnergyDistributionMesh;
        part voxel000 : ProgrammableMatterVoxel;
        part voxel001 : ProgrammableMatterVoxel;
        part voxel010 : ProgrammableMatterVoxel;
        part voxel011 : ProgrammableMatterVoxel;
        part voxel100 : ProgrammableMatterVoxel;
        part voxel101 : ProgrammableMatterVoxel;
        part voxel110 : ProgrammableMatterVoxel;
        part voxel111 : ProgrammableMatterVoxel;

        connect userProgramPort to controller.programPort;
        connect externalPowerPort to energyMesh.inputPower;
        connect energyMesh.distributedPower to voxel000.powerPort;
        connect energyMesh.distributedPower to voxel001.powerPort;
        connect energyMesh.distributedPower to voxel010.powerPort;
        connect energyMesh.distributedPower to voxel011.powerPort;
        connect energyMesh.distributedPower to voxel100.powerPort;
        connect energyMesh.distributedPower to voxel101.powerPort;
        connect energyMesh.distributedPower to voxel110.powerPort;
        connect energyMesh.distributedPower to voxel111.powerPort;

        connect controller.voxelCommandPort to voxel000.actuationPort;
        connect controller.voxelCommandPort to voxel001.actuationPort;
        connect controller.voxelCommandPort to voxel010.actuationPort;
        connect controller.voxelCommandPort to voxel011.actuationPort;
        connect controller.voxelCommandPort to voxel100.actuationPort;
        connect controller.voxelCommandPort to voxel101.actuationPort;
        connect controller.voxelCommandPort to voxel110.actuationPort;
        connect controller.voxelCommandPort to voxel111.actuationPort;

        connect voxel000.eastPort to voxel100.westPort;
        connect voxel001.eastPort to voxel101.westPort;
        connect voxel010.eastPort to voxel110.westPort;
        connect voxel011.eastPort to voxel111.westPort;

        connect voxel000.northPort to voxel010.southPort;
        connect voxel001.northPort to voxel011.southPort;
        connect voxel100.northPort to voxel110.southPort;
        connect voxel101.northPort to voxel111.southPort;

        connect voxel000.upPort to voxel001.downPort;
        connect voxel010.upPort to voxel011.downPort;
        connect voxel100.upPort to voxel101.downPort;
        connect voxel110.upPort to voxel111.downPort;

        action acceptShapeProgram {
            in item requestedProgram : ShapeProgram;
            out item acceptedProgram : ShapeProgram;
        }

        action reconfigureMatter {
            in item acceptedProgram : ShapeProgram;
            out item finalStatus : MorphologyStatus;
            first controller.loadShapeProgram;
            then controller.computeVoxelAssignments;
            then voxel000.evaluateBondCommand;
            then voxel001.evaluateBondCommand;
            then voxel010.evaluateBondCommand;
            then voxel011.evaluateBondCommand;
            then voxel100.evaluateBondCommand;
            then voxel101.evaluateBondCommand;
            then voxel110.evaluateBondCommand;
            then voxel111.evaluateBondCommand;
            then voxel000.actuateBondingLatches;
            then voxel001.actuateBondingLatches;
            then voxel010.actuateBondingLatches;
            then voxel011.actuateBondingLatches;
            then voxel100.actuateBondingLatches;
            then voxel101.actuateBondingLatches;
            then voxel110.actuateBondingLatches;
            then voxel111.actuateBondingLatches;
            then controller.monitorMorphology;
            then controller.publishSystemStatus;
        }

        state def AssemblyLifecycle {
            state unpowered;
            state ready;
            state receivingProgram;
            state morphing;
            state shapeLocked;
            state adaptiveMaintenance;
            state thermalProtection;
            state degradedOperation;
            state shutdown;

            initial then unpowered;

            transition unpowered_to_ready
                first unpowered
                then ready;

            transition ready_to_receivingProgram
                first ready
                then receivingProgram;

            transition receivingProgram_to_morphing
                first receivingProgram
                then morphing;

            transition morphing_to_shapeLocked
                first morphing
                then shapeLocked;

            transition shapeLocked_to_adaptiveMaintenance
                first shapeLocked
                then adaptiveMaintenance;

            transition adaptiveMaintenance_to_morphing
                first adaptiveMaintenance
                then morphing;

            transition morphing_to_thermalProtection
                first morphing
                then thermalProtection;

            transition thermalProtection_to_degradedOperation
                first thermalProtection
                then degradedOperation;

            transition degradedOperation_to_shutdown
                first degradedOperation
                then shutdown;
        }
    }

    requirement def PrimaryFunctionRequirement {
        subject system : ProgrammableMatterAssembly;
        require constraint {
            system.primaryFunction == "Reconfigure a lattice of addressable matter voxels into commanded three-dimensional shapes while maintaining structural integrity, power continuity, and distributed coordination."
        }
    }

    requirement def ShapeReconfigurationRequirement {
        subject system : ProgrammableMatterAssembly;
        require constraint {
            system.maximumShapeTransitionTime <= 10000.0 [ms]
        }
    }

    requirement def VoxelResolutionRequirement {
        subject system : ProgrammableMatterAssembly;
        require constraint {
            system.nominalVoxelEdgeLength <= 2.0 [mm]
        }
    }

    requirement def StructuralLoadRequirement {
        subject system : ProgrammableMatterAssembly;
        require constraint {
            system.maximumSurfaceLoad >= 120.0 [N]
        }
    }

    requirement def ThermalSafetyRequirement {
        subject system : ProgrammableMatterAssembly;
        require constraint {
            system.maximumOperatingTemperature <= 65.0 [degC]
        }
    }

    requirement def DistributedCoordinationRequirement {
        subject voxel : ProgrammableMatterVoxel;
        require constraint {
            voxel.maxBondForce >= 1.5 [N]
        }
    }

    requirement def EnergyContinuityRequirement {
        subject mesh : EnergyDistributionMesh;
        require constraint {
            mesh.minimumReserveEnergy >= 5000.0 [J]
        }
    }

    satisfy PrimaryFunctionRequirement by ProgrammableMatterAssembly;
    satisfy ShapeReconfigurationRequirement by ProgrammableMatterAssembly;
    satisfy VoxelResolutionRequirement by ProgrammableMatterAssembly;
    satisfy StructuralLoadRequirement by ProgrammableMatterAssembly;
    satisfy ThermalSafetyRequirement by ProgrammableMatterAssembly;
    satisfy DistributedCoordinationRequirement by ProgrammableMatterVoxel;
    satisfy EnergyContinuityRequirement by EnergyDistributionMesh;
}

package PumpingSubsystemModel {

    import ScalarValues::*;
    import ISQ::*;
    import SI::*;

    attribute def Pressure {
        :> scalar;
        unit = "Pa";
    }

    attribute def VolumeFlowRate {
        :> scalar;
        unit = "m^3/s";
    }

    attribute def Temperature {
        :> scalar;
        unit = "K";
    }

    attribute def RotationalSpeed {
        :> scalar;
        unit = "rev/min";
    }

    attribute def Power {
        :> scalar;
        unit = "W";
    }

    attribute def Voltage {
        :> scalar;
        unit = "V";
    }

    attribute def Current {
        :> scalar;
        unit = "A";
    }

    attribute def Efficiency {
        :> scalar;
        unit = "1";
    }

    attribute def Duration {
        :> scalar;
        unit = "s";
    }

    item def WorkingFluid {
        attribute temperature : Temperature;
        attribute staticPressure : Pressure;
        attribute volumetricFlow : VolumeFlowRate;
        attribute contaminationIndex : Real;
    }

    item def ElectricalPower {
        attribute voltage : Voltage;
        attribute current : Current;
        attribute realPower : Power;
    }

    item def ControlSignal {
        attribute commandSpeed : RotationalSpeed;
        attribute enable : Boolean;
        attribute resetFault : Boolean;
    }

    item def PumpStatus {
        attribute actualSpeed : RotationalSpeed;
        attribute dischargePressure : Pressure;
        attribute measuredFlow : VolumeFlowRate;
        attribute running : Boolean;
        attribute faultActive : Boolean;
        attribute faultCode : String;
    }

    port def FluidInletPort {
        in item fluidIn : WorkingFluid;
        attribute allowablePressure : Pressure;
    }

    port def FluidOutletPort {
        out item fluidOut : WorkingFluid;
        attribute ratedPressure : Pressure;
    }

    port def PowerInputPort {
        in item powerIn : ElectricalPower;
    }

    port def CommandInputPort {
        in item commandIn : ControlSignal;
    }

    port def StatusOutputPort {
        out item statusOut : PumpStatus;
    }

    part def CirculatorPump {
        attribute ratedFlow : VolumeFlowRate = 0.012;
        attribute ratedDifferentialPressure : Pressure = 180000.0;
        attribute maximumDifferentialPressure : Pressure = 240000.0;
        attribute minimumFlow : VolumeFlowRate = 0.0015;
        attribute maximumFlow : VolumeFlowRate = 0.018;
        attribute ratedSpeed : RotationalSpeed = 3600.0;
        attribute minimumSpeed : RotationalSpeed = 900.0;
        attribute maximumSpeed : RotationalSpeed = 4200.0;
        attribute hydraulicEfficiency : Efficiency = 0.68;
        attribute motorEfficiency : Efficiency = 0.91;
        attribute nominalPower : Power = 2200.0;
        attribute casingPressureLimit : Pressure = 600000.0;
        attribute dryRunDetectionTime : Duration = 3.0;
        attribute inletPressure : Pressure;
        attribute outletPressure : Pressure;
        attribute differentialPressure : Pressure;
        attribute actualFlow : VolumeFlowRate;
        attribute actualSpeed : RotationalSpeed;
        attribute enabled : Boolean;
        attribute running : Boolean;
        attribute faultActive : Boolean;
        attribute faultCode : String;

        port suction : FluidInletPort;
        port discharge : FluidOutletPort;
        port electricalSupply : PowerInputPort;
        port speedCommand : CommandInputPort;
        port pumpStatus : StatusOutputPort;

        constraint pressureRise {
            differentialPressure == outletPressure - inletPressure;
        }

        constraint operatingEnvelope {
            actualFlow >= minimumFlow and actualFlow <= maximumFlow;
            actualSpeed >= minimumSpeed and actualSpeed <= maximumSpeed;
            differentialPressure <= maximumDifferentialPressure;
            outletPressure <= casingPressureLimit;
        }

        action startPump {
            in command : ControlSignal;
            out status : PumpStatus;
            first startCheck;
            then rampMotor;
            then establishFlow;
            action startCheck {
                assert command.enable == true;
                assert faultActive == false;
            }
            action rampMotor {
                actualSpeed := command.commandSpeed;
                running := true;
            }
            action establishFlow {
                actualFlow := ratedFlow * actualSpeed / ratedSpeed;
                differentialPressure := ratedDifferentialPressure * (actualSpeed / ratedSpeed) * (actualSpeed / ratedSpeed);
                status.running := running;
                status.actualSpeed := actualSpeed;
                status.measuredFlow := actualFlow;
                status.dischargePressure := outletPressure;
            }
        }

        action stopPump {
            out status : PumpStatus;
            first removeTorque;
            then confirmStopped;
            action removeTorque {
                actualSpeed := 0.0;
                actualFlow := 0.0;
                running := false;
            }
            action confirmStopped {
                status.running := false;
                status.actualSpeed := 0.0;
                status.measuredFlow := 0.0;
            }
        }

        action detectFault {
            out status : PumpStatus;
            if differentialPressure > maximumDifferentialPressure then overPressureFault;
            if actualFlow < minimumFlow and running == true then dryRunFault;
            if outletPressure > casingPressureLimit then casingLimitFault;
            action overPressureFault {
                faultActive := true;
                faultCode := "PUMP_OVER_DIFFERENTIAL_PRESSURE";
            }
            action dryRunFault {
                faultActive := true;
                faultCode := "PUMP_DRY_RUN_OR_BLOCKED_SUCTION";
            }
            action casingLimitFault {
                faultActive := true;
                faultCode := "PUMP_CASING_PRESSURE_LIMIT_EXCEEDED";
            }
            status.faultActive := faultActive;
            status.faultCode := faultCode;
        }

        state def PumpOperatingState {
            state off;
            state ready;
            state starting;
            state runningState;
            state stopping;
            state faulted;

            entry; then off;

            transition off_to_ready first off accept ControlSignal
                if commandIn.enable == false and faultActive == false
                then ready;

            transition ready_to_starting first ready accept ControlSignal
                if commandIn.enable == true and commandIn.commandSpeed >= minimumSpeed
                then starting;

            transition starting_to_running first starting
                if actualSpeed >= minimumSpeed and actualFlow >= minimumFlow
                then runningState;

            transition running_to_stopping first runningState accept ControlSignal
                if commandIn.enable == false
                then stopping;

            transition stopping_to_ready first stopping
                if actualSpeed == 0.0
                then ready;

            transition any_to_fault first off then faulted
                if faultActive == true;

            transition ready_to_fault first ready then faulted
                if faultActive == true;

            transition starting_to_fault first starting then faulted
                if faultActive == true;

            transition running_to_fault first runningState then faulted
                if faultActive == true;

            transition fault_to_ready first faulted accept ControlSignal
                if commandIn.resetFault == true and commandIn.enable == false
                then ready;
        }
    }

    part def SuctionStrainer {
        attribute meshRating : Real = 500.0;
        attribute cleanPressureDrop : Pressure = 8000.0;
        attribute cloggedPressureDropLimit : Pressure = 40000.0;
        attribute measuredPressureDrop : Pressure;
        attribute clogged : Boolean;

        port inlet : FluidInletPort;
        port outlet : FluidOutletPort;

        constraint clogDetection {
            clogged == (measuredPressureDrop >= cloggedPressureDropLimit);
        }
    }

    part def CheckValve {
        attribute crackingPressure : Pressure = 5000.0;
        attribute reverseLeakageFlow : VolumeFlowRate = 0.00002;
        attribute open : Boolean;

        port inlet : FluidInletPort;
        port outlet : FluidOutletPort;

        constraint openCondition {
            open == (inlet.allowablePressure + crackingPressure <= outlet.ratedPressure);
        }
    }

    part def IsolationValve {
        attribute commandedOpen : Boolean;
        attribute positionOpen : Boolean;
        attribute fullOpenPressureDrop : Pressure = 3000.0;

        port inlet : FluidInletPort;
        port outlet : FluidOutletPort;

        action openValve {
            positionOpen := true;
            commandedOpen := true;
        }

        action closeValve {
            positionOpen := false;
            commandedOpen := false;
        }
    }

    part def PressureSensor {
        attribute rangeMin : Pressure = 0.0;
        attribute rangeMax : Pressure = 700000.0;
        attribute accuracy : Pressure = 1000.0;
        attribute measuredPressure : Pressure;

        port processPort : FluidInletPort;
        port statusPort : StatusOutputPort;
    }

    part def FlowSensor {
        attribute rangeMin : VolumeFlowRate = 0.0;
        attribute rangeMax : VolumeFlowRate = 0.025;
        attribute accuracy : VolumeFlowRate = 0.0002;
        attribute measuredFlow : VolumeFlowRate;

        port processPort : FluidOutletPort;
        port statusPort : StatusOutputPort;
    }

    part def PumpController {
        attribute targetFlow : VolumeFlowRate = 0.010;
        attribute commandedSpeed : RotationalSpeed;
        attribute minimumCommandSpeed : RotationalSpeed = 900.0;
        attribute maximumCommandSpeed : RotationalSpeed = 4200.0;
        attribute proportionalGain : Real = 85000.0;
        attribute enableRequest : Boolean;
        attribute resetRequest : Boolean;
        attribute faultLatched : Boolean;

        port powerInput : PowerInputPort;
        port pumpCommand : CommandInputPort;
        port pumpFeedback : StatusOutputPort;

        action computeSpeedCommand {
            in measured : PumpStatus;
            out command : ControlSignal;
            attribute flowError : VolumeFlowRate;
            flowError := targetFlow - measured.measuredFlow;
            commandedSpeed := measured.actualSpeed + proportionalGain * flowError;
            if commandedSpeed < minimumCommandSpeed then commandedSpeed := minimumCommandSpeed;
            if commandedSpeed > maximumCommandSpeed then commandedSpeed := maximumCommandSpeed;
            command.commandSpeed := commandedSpeed;
            command.enable := enableRequest and not faultLatched;
            command.resetFault := resetRequest;
        }

        action latchFault {
            in measured : PumpStatus;
            if measured.faultActive == true then faultLatched := true;
            if resetRequest == true and enableRequest == false then faultLatched := false;
        }

        state def ControllerState {
            state disabled;
            state enabled;
            state regulating;
            state shutdown;
            state faultLockout;

            entry; then disabled;

            transition disabled_to_enabled first disabled
                if enableRequest == true and faultLatched == false
                then enabled;

            transition enabled_to_regulating first enabled
                if commandedSpeed >= minimumCommandSpeed
                then regulating;

            transition regulating_to_shutdown first regulating
                if enableRequest == false
                then shutdown;

            transition shutdown_to_disabled first shutdown
                if commandedSpeed == 0.0
                then disabled;

            transition regulating_to_fault first regulating
                if faultLatched == true
                then faultLockout;

            transition fault_to_disabled first faultLockout
                if resetRequest == true and enableRequest == false
                then disabled;
        }
    }

    part def PumpingSubsystem {
        attribute requiredFlow : VolumeFlowRate = 0.010;
        attribute minimumDeliveredFlow : VolumeFlowRate = 0.008;
        attribute maximumDeliveredFlow : VolumeFlowRate = 0.014;
        attribute requiredDifferentialPressure : Pressure = 150000.0;
        attribute maximumDischargePressure : Pressure = 550000.0;
        attribute nominalSupplyVoltage : Voltage = 480.0;
        attribute maximumSupplyCurrent : Current = 8.0;
        attribute subsystemAvailable : Boolean;
        attribute deliveredFlow : VolumeFlowRate;
        attribute dischargePressure : Pressure;

        port fluidSupply : FluidInletPort;
        port fluidDelivery : FluidOutletPort;
        port electricalInput : PowerInputPort;
        port controlInput : CommandInputPort;
        port healthStatus : StatusOutputPort;

        part suctionIsolationValve : IsolationValve {
            commandedOpen = true;
            positionOpen = true;
        }

        part inletStrainer : SuctionStrainer;

        part circulator : CirculatorPump;

        part dischargeCheckValve : CheckValve;

        part dischargeIsolationValve : IsolationValve {
            commandedOpen = true;
            positionOpen = true;
        }

        part suctionPressureSensor : PressureSensor;

        part dischargePressureSensor : PressureSensor;

        part deliveredFlowSensor : FlowSensor;

        part controller : PumpController {
            targetFlow = requiredFlow;
        }

        connect fluidSupply to suctionIsolationValve.inlet;
        connect suctionIsolationValve.outlet to inletStrainer.inlet;
        connect inletStrainer.outlet to circulator.suction;
        connect circulator.discharge to dischargeCheckValve.inlet;
        connect dischargeCheckValve.outlet to dischargeIsolationValve.inlet;
        connect dischargeIsolationValve.outlet to fluidDelivery;

        connect electricalInput to controller.powerInput;
        connect electricalInput to circulator.electricalSupply;
        connect controlInput to controller.pumpCommand;
        connect controller.pumpCommand to circulator.speedCommand;
        connect circulator.pumpStatus to controller.pumpFeedback;
        connect circulator.pumpStatus to healthStatus;

        connect inletStrainer.outlet to suctionPressureSensor.processPort;
        connect dischargeIsolationValve.outlet to dischargePressureSensor.processPort;
        connect dischargeIsolationValve.outlet to deliveredFlowSensor.processPort;

        constraint deliveredFlowRange {
            deliveredFlow >= minimumDeliveredFlow and deliveredFlow <= maximumDeliveredFlow;
        }

        constraint pressureCapability {
            dischargePressure <= maximumDischargePressure;
            circulator.differentialPressure >= requiredDifferentialPressure;
        }

        constraint electricalLimit {
            electricalInput.powerIn.voltage == nominalSupplyVoltage;
            electricalInput.powerIn.current <= maximumSupplyCurrent;
        }

        action startSubsystem {
            first verifyValvesOpen;
            then energizeController;
            then startCirculator;
            then validateDelivery;
            action verifyValvesOpen {
                assert suctionIsolationValve.positionOpen == true;
                assert dischargeIsolationValve.positionOpen == true;
                assert inletStrainer.clogged == false;
            }
            action energizeController {
                controller.enableRequest := true;
                controller.faultLatched := false;
            }
            action startCirculator {
                circulator.startPump;
            }
            action validateDelivery {
                assert deliveredFlow >= minimumDeliveredFlow;
                assert dischargePressure <= maximumDischargePressure;
                subsystemAvailable := true;
            }
        }

        action stopSubsystem {
            first disableController;
            then stopCirculator;
            action disableController {
                controller.enableRequest := false;
            }
            action stopCirculator {
                circulator.stopPump;
                subsystemAvailable := false;
            }
        }

        action protectSubsystem {
            first evaluateStrainer;
            then evaluatePump;
            then isolateIfRequired;
            action evaluateStrainer {
                if inletStrainer.clogged == true then controller.faultLatched := true;
            }
            action evaluatePump {
                circulator.detectFault;
                if circulator.faultActive == true then controller.faultLatched := true;
            }
            action isolateIfRequired {
                if controller.faultLatched == true then dischargeIsolationValve.closeValve;
            }
        }
    }

    requirement def MoveFluidRequirement {
        subject subsystem : PumpingSubsystem;
        require constraint {
            subsystem.deliveredFlow >= subsystem.minimumDeliveredFlow and
            subsystem.deliveredFlow <= subsystem.maximumDeliveredFlow
        }
    }

    requirement def CirculatorPumpRequirement {
        subject pump : CirculatorPump;
        require constraint {
            pump.ratedFlow >= 0.010 and
            pump.ratedDifferentialPressure >= 150000.0 and
            pump.maximumDifferentialPressure >= 180000.0
        }
    }

    requirement def PressureContainmentRequirement {
        subject subsystem : PumpingSubsystem;
        require constraint {
            subsystem.dischargePressure <= subsystem.maximumDischargePressure and
            subsystem.circulator.outletPressure <= subsystem.circulator.casingPressureLimit
        }
    }

    requirement def FaultProtectionRequirement {
        subject subsystem : PumpingSubsystem;
        require constraint {
            subsystem.inletStrainer.clogged == false implies subsystem.controller.faultLatched == false
        }
    }

    requirement def ElectricalSupplyRequirement {
        subject subsystem : PumpingSubsystem;
        require constraint {
            subsystem.electricalInput.powerIn.voltage == subsystem.nominalSupplyVoltage and
            subsystem.electricalInput.powerIn.current <= subsystem.maximumSupplyCurrent
        }
    }

    requirement def CheckValveRequirement {
        subject valve : CheckValve;
        require constraint {
            valve.reverseLeakageFlow <= 0.00002
        }
    }

    requirement def InstrumentationRequirement {
        subject subsystem : PumpingSubsystem;
        require constraint {
            subsystem.deliveredFlowSensor.rangeMax >= subsystem.maximumDeliveredFlow and
            subsystem.dischargePressureSensor.rangeMax >= subsystem.maximumDischargePressure
        }
    }

    part circulatingWaterPumpingSubsystem : PumpingSubsystem {
        requiredFlow = 0.010;
        minimumDeliveredFlow = 0.008;
        maximumDeliveredFlow = 0.014;
        requiredDifferentialPressure = 150000.0;
        maximumDischargePressure = 550000.0;
        nominalSupplyVoltage = 480.0;
        maximumSupplyCurrent = 8.0;
    }

    satisfy MoveFluidRequirement by circulatingWaterPumpingSubsystem;
    satisfy PressureContainmentRequirement by circulatingWaterPumpingSubsystem;
    satisfy ElectricalSupplyRequirement by circulatingWaterPumpingSubsystem;
    satisfy InstrumentationRequirement by circulatingWaterPumpingSubsystem;
    satisfy CirculatorPumpRequirement by circulatingWaterPumpingSubsystem.circulator;
    satisfy CheckValveRequirement by circulatingWaterPumpingSubsystem.dischargeCheckValve;
}

package IRIS_System_Model {

  import ScalarValues::*;
  import ISQ::*;

  attribute def Percent :> Real;
  attribute def RiskScore :> Real;
  attribute def ConfidenceScore :> Real;

  item def RawObservation {
    attribute timestamp : Time;
    attribute sourceId : String;
    attribute payloadSize : Mass;
    attribute integrity : Percent;
  }

  item def ImageFrame :> RawObservation {
    attribute width : Integer;
    attribute height : Integer;
    attribute exposureTime : Time;
    attribute spectralBand : String;
  }

  item def EnvironmentalReading :> RawObservation {
    attribute temperature : Temperature;
    attribute humidity : Percent;
    attribute pressure : Pressure;
    attribute airborneParticleDensity : Real;
  }

  item def TargetCue {
    attribute targetId : String;
    attribute bearing : Angle;
    attribute range : Length;
    attribute confidence : ConfidenceScore;
  }

  item def SituationalAssessment {
    attribute assessedAreaId : String;
    attribute anomalyCount : Integer;
    attribute highestRisk : RiskScore;
    attribute confidence : ConfidenceScore;
    attribute summary : String;
  }

  item def MissionCommand {
    attribute missionId : String;
    attribute surveyAreaId : String;
    attribute priority : Integer;
    attribute requestedCoverage : Percent;
    attribute maximumDuration : Time;
  }

  item def HealthReport {
    attribute reportingNode : String;
    attribute batteryStateOfCharge : Percent;
    attribute processorLoad : Percent;
    attribute thermalMargin : Temperature;
    attribute degraded : Boolean;
  }

  port def ObservationInputPort {
    in item observation : RawObservation;
  }

  port def FrameOutputPort {
    out item frame : ImageFrame;
  }

  port def ReadingOutputPort {
    out item reading : EnvironmentalReading;
  }

  port def CuePort {
    out item cue : TargetCue;
  }

  port def AssessmentPort {
    out item assessment : SituationalAssessment;
  }

  port def CommandPort {
    in item command : MissionCommand;
  }

  port def HealthPort {
    out item health : HealthReport;
  }

  port def PowerPort {
    in attribute suppliedPower : Power;
    out attribute demandedPower : Power;
  }

  port def DataLinkPort {
    in item inboundCommand : MissionCommand;
    out item outboundAssessment : SituationalAssessment;
    out item outboundHealth : HealthReport;
  }

  action def AcquireObservations {
    in item command : MissionCommand;
    out item frame : ImageFrame;
    out item reading : EnvironmentalReading;
  }

  action def FuseSensorData {
    in item frame : ImageFrame;
    in item reading : EnvironmentalReading;
    out item cue : TargetCue;
  }

  action def AssessSituation {
    in item cue : TargetCue;
    in item reading : EnvironmentalReading;
    out item assessment : SituationalAssessment;
  }

  action def ReportAssessment {
    in item assessment : SituationalAssessment;
    out item transmittedAssessment : SituationalAssessment;
  }

  action def MonitorHealth {
    in attribute batteryStateOfCharge : Percent;
    in attribute processorLoad : Percent;
    in attribute thermalMargin : Temperature;
    out item health : HealthReport;
  }

  state def IRISOperatingState {
    entry action initialize;
    state Idle;
    state MissionPlanning;
    state Surveying;
    state Processing;
    state Reporting;
    state Degraded;
    state SafeShutdown;

    transition first Idle;
    transition Idle_to_MissionPlanning
      first Idle
      then MissionPlanning
      accept MissionCommand;

    transition MissionPlanning_to_Surveying
      first MissionPlanning
      then Surveying;

    transition Surveying_to_Processing
      first Surveying
      then Processing;

    transition Processing_to_Reporting
      first Processing
      then Reporting;

    transition Reporting_to_Surveying
      first Reporting
      then Surveying;

    transition Reporting_to_Idle
      first Reporting
      then Idle;

    transition Any_to_Degraded
      first Idle
      then Degraded
      if healthDegraded;

    transition Surveying_to_Degraded
      first Surveying
      then Degraded
      if healthDegraded;

    transition Processing_to_Degraded
      first Processing
      then Degraded
      if healthDegraded;

    transition Degraded_to_SafeShutdown
      first Degraded
      then SafeShutdown
      if batteryCritical;

    transition Degraded_to_Surveying
      first Degraded
      then Surveying
      if recovered;
  }

  part def ElectroOpticalCamera {
    attribute resolutionHorizontal : Integer = 4096;
    attribute resolutionVertical : Integer = 3072;
    attribute frameRate : Frequency = 30 [Hz];
    attribute fieldOfView : Angle = 78 [deg];
    attribute mass : Mass = 0.42 [kg];

    port power : PowerPort;
    port frames : FrameOutputPort;

    perform action acquireFrame : AcquireObservations;
  }

  part def EnvironmentalSensorSuite {
    attribute temperatureAccuracy : Temperature = 0.5 [K];
    attribute humidityAccuracy : Percent = 2.0;
    attribute pressureAccuracy : Pressure = 25 [Pa];
    attribute sampleRate : Frequency = 10 [Hz];
    attribute mass : Mass = 0.31 [kg];

    port power : PowerPort;
    port readings : ReadingOutputPort;

    perform action sampleEnvironment : AcquireObservations;
  }

  part def NavigationUnit {
    attribute positionAccuracy : Length = 0.2 [m];
    attribute attitudeAccuracy : Angle = 0.5 [deg];
    attribute updateRate : Frequency = 50 [Hz];
    attribute mass : Mass = 0.28 [kg];

    port power : PowerPort;
    port health : HealthPort;
  }

  part def SensorFusionProcessor {
    attribute computeThroughput : Real = 18.0;
    attribute memoryCapacity : Real = 64.0;
    attribute nominalPowerDemand : Power = 45 [W];
    attribute maximumProcessorLoad : Percent = 95.0;

    port power : PowerPort;
    port observationInput : ObservationInputPort;
    port targetCueOutput : CuePort;
    port health : HealthPort;

    perform action fuse : FuseSensorData;
  }

  part def AssessmentEngine {
    attribute minimumConfidenceForReport : ConfidenceScore = 0.72;
    attribute maximumAllowedFalseAlarmRate : Percent = 5.0;
    attribute riskThresholdForAlert : RiskScore = 0.65;

    port power : PowerPort;
    port cueInput : ObservationInputPort;
    port assessmentOutput : AssessmentPort;
    port health : HealthPort;

    perform action assess : AssessSituation;
  }

  part def CommunicationsModule {
    attribute uplinkRate : Real = 20.0;
    attribute downlinkRate : Real = 80.0;
    attribute nominalRange : Length = 5000 [m];
    attribute transmitPower : Power = 12 [W];

    port power : PowerPort;
    port datalink : DataLinkPort;

    perform action report : ReportAssessment;
  }

  part def PowerSubsystem {
    attribute storedEnergy : Energy = 620 [Wh];
    attribute nominalVoltage : ElectricPotential = 28 [V];
    attribute maximumContinuousPower : Power = 220 [W];
    attribute criticalStateOfCharge : Percent = 12.0;

    port cameraPower : PowerPort;
    port sensorPower : PowerPort;
    port navigationPower : PowerPort;
    port processorPower : PowerPort;
    port assessmentPower : PowerPort;
    port communicationsPower : PowerPort;
    port health : HealthPort;

    perform action monitor : MonitorHealth;
  }

  part def HumanOperatorStation {
    attribute operatorId : String;
    attribute displayRefreshRate : Frequency = 60 [Hz];
    attribute minimumRequiredAssessmentConfidence : ConfidenceScore = 0.70;

    port missionInterface : DataLinkPort;
  }

  part def IRIS {
    attribute systemName : String = "IRIS - Integrated Reconnaissance and Inspection System";
    attribute primaryFunction : String = "Autonomously collect multi-sensor observations, identify mission-relevant anomalies, assess risk, and report actionable situational information to an operator.";
    attribute operationalEndurance : Time = 4 [h];
    attribute surveyCoverageRate : Real = 12000.0;
    attribute totalMass : Mass = 8.7 [kg];
    attribute nominalPowerDemand : Power = 135 [W];
    attribute minimumReportConfidence : ConfidenceScore = 0.72;

    part camera : ElectroOpticalCamera;
    part environmentalSensors : EnvironmentalSensorSuite;
    part navigation : NavigationUnit;
    part fusionProcessor : SensorFusionProcessor;
    part assessmentEngine : AssessmentEngine;
    part communications : CommunicationsModule;
    part powerSubsystem : PowerSubsystem;

    port commandAndTelemetry : DataLinkPort;
    port healthOutput : HealthPort;

    connect powerSubsystem.cameraPower to camera.power;
    connect powerSubsystem.sensorPower to environmentalSensors.power;
    connect powerSubsystem.navigationPower to navigation.power;
    connect powerSubsystem.processorPower to fusionProcessor.power;
    connect powerSubsystem.assessmentPower to assessmentEngine.power;
    connect powerSubsystem.communicationsPower to communications.power;

    connect camera.frames to fusionProcessor.observationInput;
    connect environmentalSensors.readings to fusionProcessor.observationInput;
    connect fusionProcessor.targetCueOutput to assessmentEngine.cueInput;
    connect assessmentEngine.assessmentOutput to communications.datalink;
    connect communications.datalink to commandAndTelemetry;

    connect powerSubsystem.health to healthOutput;
    connect fusionProcessor.health to healthOutput;
    connect assessmentEngine.health to healthOutput;
    connect navigation.health to healthOutput;
    connect communications.datalink to commandAndTelemetry;

    perform action missionAcquisition : AcquireObservations;
    perform action dataFusion : FuseSensorData;
    perform action situationAssessment : AssessSituation;
    perform action telemetryReporting : ReportAssessment;
    exhibit state operatingState : IRISOperatingState;
  }

  part def IRISOperationalContext {
    part iris : IRIS;
    part operatorStation : HumanOperatorStation;

    connect iris.commandAndTelemetry to operatorStation.missionInterface;
  }

  requirement def PrimaryFunctionRequirement {
    subject iris : IRIS;
    require constraint {
      iris.primaryFunction == "Autonomously collect multi-sensor observations, identify mission-relevant anomalies, assess risk, and report actionable situational information to an operator."
    }
  }

  requirement def CoverageRequirement {
    subject iris : IRIS;
    attribute requiredCoverage : Percent = 95.0;
    require constraint {
      iris.operationalEndurance >= 4 [h]
    }
  }

  requirement def AssessmentConfidenceRequirement {
    subject iris : IRIS;
    attribute minimumConfidence : ConfidenceScore = 0.72;
    require constraint {
      iris.minimumReportConfidence >= minimumConfidence
    }
  }

  requirement def PowerRequirement {
    subject iris : IRIS;
    attribute maximumNominalPower : Power = 150 [W];
    require constraint {
      iris.nominalPowerDemand <= maximumNominalPower
    }
  }

  requirement def MassRequirement {
    subject iris : IRIS;
    attribute maximumMass : Mass = 10 [kg];
    require constraint {
      iris.totalMass <= maximumMass
    }
  }

  requirement def CommunicationsRequirement {
    subject iris : IRIS;
    require constraint {
      iris.communications.nominalRange >= 5000 [m]
    }
  }

  requirement def HealthManagementRequirement {
    subject iris : IRIS;
    attribute criticalChargeLimit : Percent = 12.0;
    require constraint {
      iris.powerSubsystem.criticalStateOfCharge <= criticalChargeLimit
    }
  }

  satisfy PrimaryFunctionRequirement by IRIS;
  satisfy CoverageRequirement by IRIS;
  satisfy AssessmentConfidenceRequirement by AssessmentEngine;
  satisfy PowerRequirement by PowerSubsystem;
  satisfy MassRequirement by IRIS;
  satisfy CommunicationsRequirement by CommunicationsModule;
  satisfy HealthManagementRequirement by PowerSubsystem;

  action def ExecuteIRISMission {
    in item missionCommand : MissionCommand;
    out item finalAssessment : SituationalAssessment;
    out item finalHealthReport : HealthReport;

    first start;
    then acquire : AcquireObservations;
    then fuse : FuseSensorData;
    then assess : AssessSituation;
    then report : ReportAssessment;
    then monitor : MonitorHealth;
    then done;

    flow missionCommand to acquire.command;
    flow acquire.frame to fuse.frame;
    flow acquire.reading to fuse.reading;
    flow fuse.cue to assess.cue;
    flow acquire.reading to assess.reading;
    flow assess.assessment to report.assessment;
    flow report.transmittedAssessment to finalAssessment;
    flow monitor.health to finalHealthReport;
  }

}

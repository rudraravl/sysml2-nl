package WaterMeterSystemModel {

  import ScalarValues::*;
  import ISQ::*;
  import SI::*;

  attribute def Volume :> ISQ::volume {
    unit = SI::litre;
  }

  attribute def FlowRate :> ISQ::volumeFlowRate {
    unit = SI::litre / SI::second;
  }

  attribute def Pressure :> ISQ::pressure {
    unit = SI::pascal;
  }

  attribute def Temperature :> ISQ::temperature {
    unit = SI::degreeCelsius;
  }

  attribute def BatteryCharge :> ScalarValues::Real {
    unit = SI::percent;
  }

  attribute def SignalStrength :> ScalarValues::Real {
    unit = SI::decibel;
  }

  attribute def Timestamp :> ScalarValues::String;

  enum def MeterOperatingMode {
    enum idle;
    enum measuring;
    enum transmitting;
    enum faulted;
    enum service;
  }

  enum def FlowDirection {
    enum forward;
    enum reverse;
    enum noFlow;
  }

  enum def AlarmKind {
    enum leakDetected;
    enum reverseFlowDetected;
    enum tamperDetected;
    enum lowBattery;
    enum sensorFault;
    enum communicationFault;
    enum overRangeFlow;
  }

  item def Water {
    attribute temperature : Temperature;
    attribute pressure : Pressure;
    attribute qualityIndicator : ScalarValues::Real;
  }

  item def WaterFlow {
    attribute rate : FlowRate;
    attribute direction : FlowDirection;
    attribute pressure : Pressure;
    attribute temperature : Temperature;
  }

  item def MeterReading {
    attribute cumulativeVolume : Volume;
    attribute instantaneousFlowRate : FlowRate;
    attribute direction : FlowDirection;
    attribute timestamp : Timestamp;
    attribute batteryCharge : BatteryCharge;
  }

  item def AlarmReport {
    attribute kind : AlarmKind;
    attribute timestamp : Timestamp;
    attribute active : ScalarValues::Boolean;
    attribute severity : ScalarValues::Integer;
  }

  item def ConfigurationCommand {
    attribute samplingPeriod_s : ScalarValues::Real;
    attribute reportingPeriod_s : ScalarValues::Real;
    attribute leakThreshold_L_per_h : ScalarValues::Real;
    attribute reverseFlowEnabled : ScalarValues::Boolean;
  }

  port def HydraulicInletPort {
    in item incomingWaterFlow : WaterFlow;
  }

  port def HydraulicOutletPort {
    out item outgoingWaterFlow : WaterFlow;
  }

  port def ReadingOutputPort {
    out item reading : MeterReading;
    out item alarm : AlarmReport;
  }

  port def CommandInputPort {
    in item command : ConfigurationCommand;
  }

  port def ElectricalPowerPort {
    in attribute supplyVoltage_V : ScalarValues::Real;
    out attribute loadCurrent_mA : ScalarValues::Real;
  }

  port def LocalDisplayPort {
    out attribute visibleVolume_L : ScalarValues::Real;
    out attribute visibleFlow_L_per_min : ScalarValues::Real;
    out attribute alarmIconActive : ScalarValues::Boolean;
  }

  part def FlowBody {
    port inlet : HydraulicInletPort;
    port outlet : HydraulicOutletPort;

    attribute nominalDiameter_mm : ScalarValues::Real;
    attribute maximumWorkingPressure : Pressure;
    attribute pressureLossAtNominalFlow : Pressure;

    item flowThroughMeter : WaterFlow;
  }

  part def FlowSensor {
    port sensedFlowIn : HydraulicInletPort;

    attribute minimumDetectableFlow : FlowRate;
    attribute maximumMeasurableFlow : FlowRate;
    attribute measurementErrorPercent : ScalarValues::Real;
    attribute pulseConstant_L_per_pulse : ScalarValues::Real;

    out attribute measuredFlowRate : FlowRate;
    out attribute measuredDirection : FlowDirection;
    out attribute generatedPulseCount : ScalarValues::Integer;
  }

  part def VolumeIntegrator {
    in attribute flowRate : FlowRate;
    in attribute flowDirection : FlowDirection;

    attribute accumulatedForwardVolume : Volume;
    attribute accumulatedReverseVolume : Volume;
    attribute netVolume : Volume;
    attribute integrationPeriod_s : ScalarValues::Real;

    action integrateFlow {
      in attribute sampleFlowRate : FlowRate;
      in attribute sampleDirection : FlowDirection;
      in attribute deltaTime_s : ScalarValues::Real;
      out attribute volumeIncrement : Volume;
    }
  }

  part def TemperatureSensor {
    in item sampledWater : Water;
    out attribute measuredTemperature : Temperature;

    attribute measurementError_degC : ScalarValues::Real;
  }

  part def PressureSensor {
    in item sampledWater : Water;
    out attribute measuredPressure : Pressure;

    attribute measurementError_Pa : ScalarValues::Real;
  }

  part def MeterController {
    in attribute flowRate : FlowRate;
    in attribute direction : FlowDirection;
    in attribute cumulativeVolume : Volume;
    in attribute batteryCharge : BatteryCharge;
    in attribute pressure : Pressure;
    in attribute temperature : Temperature;

    out item currentReading : MeterReading;
    out item activeAlarm : AlarmReport;
    out attribute operatingMode : MeterOperatingMode;

    attribute samplingPeriod_s : ScalarValues::Real = 1.0;
    attribute reportingPeriod_s : ScalarValues::Real = 900.0;
    attribute leakThreshold_L_per_h : ScalarValues::Real = 5.0;
    attribute zeroFlowThreshold_L_per_h : ScalarValues::Real = 0.5;
    attribute lowBatteryThreshold_percent : BatteryCharge = 15.0;

    action acquireMeasurement {
      in attribute sampledFlowRate : FlowRate;
      in attribute sampledDirection : FlowDirection;
      in attribute sampledVolume : Volume;
      out item reading : MeterReading;
    }

    action evaluateAlarms {
      in item reading : MeterReading;
      in attribute battery : BatteryCharge;
      out item alarm : AlarmReport;
    }

    action applyConfiguration {
      in item command : ConfigurationCommand;
      out attribute newSamplingPeriod_s : ScalarValues::Real;
      out attribute newReportingPeriod_s : ScalarValues::Real;
    }

    state behavior controllerStateMachine {
      entry action initializeController;

      state initializing;
      state idle;
      state measuring;
      state evaluating;
      state reporting;
      state serviceMode;
      state fault;

      transition first initializing;

      transition initializing_to_idle
        first initializing
        then idle;

      transition idle_to_measuring
        first idle
        then measuring
        accept after samplingPeriod_s;

      transition measuring_to_evaluating
        first measuring
        then evaluating
        do acquireMeasurement;

      transition evaluating_to_reporting
        first evaluating
        then reporting
        if activeAlarm.active == true;

      transition evaluating_to_idle
        first evaluating
        then idle
        if activeAlarm.active == false;

      transition reporting_to_idle
        first reporting
        then idle;

      transition any_to_service
        first idle
        then serviceMode
        accept ConfigurationCommand;

      transition service_to_idle
        first serviceMode
        then idle
        do applyConfiguration;

      transition any_to_fault
        first measuring
        then fault
        if flowRate > 100.0 [SI::litre / SI::second];

      transition fault_to_service
        first fault
        then serviceMode
        accept ConfigurationCommand;
    }
  }

  part def CommunicationModule {
    port readingOut : ReadingOutputPort;
    port commandIn : CommandInputPort;
    port power : ElectricalPowerPort;

    in item readingToTransmit : MeterReading;
    in item alarmToTransmit : AlarmReport;
    out item receivedCommand : ConfigurationCommand;

    attribute signalStrength : SignalStrength;
    attribute reportingInterval_s : ScalarValues::Real;
    attribute lastSuccessfulTransmission : Timestamp;

    action transmitReading {
      in item reading : MeterReading;
      out attribute transmissionAccepted : ScalarValues::Boolean;
    }

    action transmitAlarm {
      in item alarm : AlarmReport;
      out attribute alarmAccepted : ScalarValues::Boolean;
    }
  }

  part def RegisterDisplay {
    port displayPort : LocalDisplayPort;

    in attribute displayedVolume : Volume;
    in attribute displayedFlowRate : FlowRate;
    in item displayedAlarm : AlarmReport;

    attribute digitCount : ScalarValues::Integer = 8;
    attribute updatePeriod_s : ScalarValues::Real = 1.0;
  }

  part def BatteryPack {
    port powerOut : ElectricalPowerPort;

    attribute nominalVoltage_V : ScalarValues::Real = 3.6;
    attribute remainingCharge : BatteryCharge;
    attribute designLife_year : ScalarValues::Real = 15.0;
    attribute lowBatteryLimit : BatteryCharge = 15.0;

    action supplyPower {
      out attribute voltage_V : ScalarValues::Real;
      out attribute current_mA : ScalarValues::Real;
    }
  }

  part def TamperDetector {
    out attribute enclosureOpen : ScalarValues::Boolean;
    out attribute magneticTamperPresent : ScalarValues::Boolean;
    out item tamperAlarm : AlarmReport;

    action detectTamper {
      in attribute enclosureOpenInput : ScalarValues::Boolean;
      in attribute magneticFieldDetected : ScalarValues::Boolean;
      out item alarm : AlarmReport;
    }
  }

  part def WaterMeter {
    port waterIn : HydraulicInletPort;
    port waterOut : HydraulicOutletPort;
    port readings : ReadingOutputPort;
    port commands : CommandInputPort;

    part body : FlowBody {
      attribute nominalDiameter_mm = 20.0;
      attribute maximumWorkingPressure = 1600000.0 [SI::pascal];
      attribute pressureLossAtNominalFlow = 25000.0 [SI::pascal];
    }

    part sensor : FlowSensor {
      attribute minimumDetectableFlow = 0.00003 [SI::litre / SI::second];
      attribute maximumMeasurableFlow = 1.4 [SI::litre / SI::second];
      attribute measurementErrorPercent = 2.0;
      attribute pulseConstant_L_per_pulse = 1.0;
    }

    part integrator : VolumeIntegrator {
      attribute accumulatedForwardVolume = 0.0 [SI::litre];
      attribute accumulatedReverseVolume = 0.0 [SI::litre];
      attribute netVolume = 0.0 [SI::litre];
      attribute integrationPeriod_s = 1.0;
    }

    part temperatureSensor : TemperatureSensor {
      attribute measurementError_degC = 0.5;
    }

    part pressureSensor : PressureSensor {
      attribute measurementError_Pa = 5000.0;
    }

    part controller : MeterController;

    part radio : CommunicationModule {
      attribute signalStrength = -85.0 [SI::decibel];
      attribute reportingInterval_s = 900.0;
    }

    part display : RegisterDisplay;

    part battery : BatteryPack {
      attribute remainingCharge = 100.0 [SI::percent];
    }

    part tamperDetector : TamperDetector;

    connect waterIn to body.inlet;
    connect body.outlet to waterOut;
    connect body.inlet to sensor.sensedFlowIn;

    flow sensor.measuredFlowRate to integrator.flowRate;
    flow sensor.measuredDirection to integrator.flowDirection;

    flow sensor.measuredFlowRate to controller.flowRate;
    flow sensor.measuredDirection to controller.direction;
    flow integrator.netVolume to controller.cumulativeVolume;
    flow battery.remainingCharge to controller.batteryCharge;
    flow pressureSensor.measuredPressure to controller.pressure;
    flow temperatureSensor.measuredTemperature to controller.temperature;

    flow controller.currentReading to radio.readingToTransmit;
    flow controller.activeAlarm to radio.alarmToTransmit;
    flow controller.currentReading to readings.reading;
    flow controller.activeAlarm to readings.alarm;

    flow radio.receivedCommand to controller.applyConfiguration.command;
    connect commands to radio.commandIn;

    flow integrator.netVolume to display.displayedVolume;
    flow sensor.measuredFlowRate to display.displayedFlowRate;
    flow controller.activeAlarm to display.displayedAlarm;

    connect battery.powerOut to radio.power;

    objective primaryFunction {
      doc
      /*
       The WaterMeter measures water passing from its inlet to its outlet,
       determines instantaneous flow rate and cumulative consumed volume,
       detects abnormal conditions such as reverse flow, leakage, tamper,
       low battery, and sensor faults, and reports validated meter readings
       locally and remotely for billing, monitoring, and maintenance.
      */
    }
  }

  part def UtilityEndpoint {
    port meterDataIn : ReadingOutputPort;
    port meterCommandOut : CommandInputPort;

    in item receivedReading : MeterReading;
    in item receivedAlarm : AlarmReport;
    out item issuedCommand : ConfigurationCommand;

    attribute endpointIdentifier : ScalarValues::String;
  }

  part def ResidentialServiceLine {
    part installedMeter : WaterMeter;
    part utilitySystem : UtilityEndpoint;

    item suppliedWater : WaterFlow {
      attribute rate = 0.12 [SI::litre / SI::second];
      attribute direction = FlowDirection::forward;
      attribute pressure = 450000.0 [SI::pascal];
      attribute temperature = 12.0 [SI::degreeCelsius];
    }

    connect installedMeter.readings to utilitySystem.meterDataIn;
    connect utilitySystem.meterCommandOut to installedMeter.commands;
  }

  requirement def MeasureWaterVolumeRequirement {
    subject meter : WaterMeter;

    require constraint {
      meter.integrator.netVolume >= 0.0 [SI::litre]
    }

    doc
    /*
     The water meter shall calculate cumulative net water volume
     passing through the meter body from inlet to outlet.
    */
  }

  requirement def FlowRateMeasurementRequirement {
    subject meter : WaterMeter;

    require constraint {
      meter.sensor.minimumDetectableFlow <= 0.00003 [SI::litre / SI::second]
    }

    require constraint {
      meter.sensor.maximumMeasurableFlow >= 1.4 [SI::litre / SI::second]
    }

    doc
    /*
     The water meter shall measure instantaneous flow rate across
     the specified residential service flow range.
    */
  }

  requirement def ReadingReportingRequirement {
    subject meter : WaterMeter;

    require constraint {
      meter.controller.reportingPeriod_s <= 900.0
    }

    doc
    /*
     The water meter shall make cumulative volume, instantaneous flow,
     flow direction, timestamp, and battery charge available to local
     display and remote communication interfaces at least every 15 minutes.
    */
  }

  requirement def ReverseFlowDetectionRequirement {
    subject meter : WaterMeter;

    require constraint {
      meter.sensor.measuredDirection == FlowDirection::reverse implies
      meter.controller.activeAlarm.kind == AlarmKind::reverseFlowDetected
    }

    doc
    /*
     The water meter shall detect and report reverse flow when measured
     flow direction is opposite the normal inlet-to-outlet direction.
    */
  }

  requirement def LeakDetectionRequirement {
    subject meter : WaterMeter;

    require constraint {
      meter.controller.leakThreshold_L_per_h <= 5.0
    }

    doc
    /*
     The water meter shall identify sustained low-level continuous flow
     as a potential leak and generate a leak alarm.
    */
  }

  requirement def LowBatteryRequirement {
    subject meter : WaterMeter;

    require constraint {
      meter.battery.remainingCharge <= meter.battery.lowBatteryLimit implies
      meter.controller.activeAlarm.kind == AlarmKind::lowBattery
    }

    doc
    /*
     The water meter shall generate a low-battery alarm when remaining
     battery charge is at or below the configured service threshold.
    */
  }

  requirement def TamperDetectionRequirement {
    subject meter : WaterMeter;

    require constraint {
      meter.tamperDetector.enclosureOpen == true or
      meter.tamperDetector.magneticTamperPresent == true implies
      meter.tamperDetector.tamperAlarm.kind == AlarmKind::tamperDetected
    }

    doc
    /*
     The water meter shall detect enclosure opening or magnetic interference
     and produce a tamper alarm.
    */
  }

  satisfy MeasureWaterVolumeRequirement by WaterMeter::integrator;
  satisfy FlowRateMeasurementRequirement by WaterMeter::sensor;
  satisfy ReadingReportingRequirement by WaterMeter::controller;
  satisfy ReverseFlowDetectionRequirement by WaterMeter::controller;
  satisfy LeakDetectionRequirement by WaterMeter::controller;
  satisfy LowBatteryRequirement by WaterMeter::battery;
  satisfy TamperDetectionRequirement by WaterMeter::tamperDetector;

  action def MeasureAndReportWaterConsumption {
    in item inletFlow : WaterFlow;
    out item outletFlow : WaterFlow;
    out item reading : MeterReading;
    out item alarm : AlarmReport;

    action senseFlow {
      in item flow : WaterFlow;
      out attribute rate : FlowRate;
      out attribute direction : FlowDirection;
    }

    action accumulateVolume {
      in attribute rate : FlowRate;
      in attribute direction : FlowDirection;
      out attribute totalVolume : Volume;
    }

    action createReading {
      in attribute totalVolume : Volume;
      in attribute rate : FlowRate;
      in attribute direction : FlowDirection;
      out item meterReading : MeterReading;
    }

    action checkForAbnormalConditions {
      in item meterReading : MeterReading;
      out item generatedAlarm : AlarmReport;
    }

    action publishReading {
      in item meterReading : MeterReading;
      in item generatedAlarm : AlarmReport;
    }

    first start;
    then senseFlow;
    then accumulateVolume;
    then createReading;
    then checkForAbnormalConditions;
    then publishReading;
    then done;
  }

}

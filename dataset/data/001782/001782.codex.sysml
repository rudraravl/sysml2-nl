package HydraulicFracturingSystemModel {

  import ScalarValues::*;
  import ISQ::*;
  import SI::*;

  attribute def PressureValue :> pressure {
    unit = "MPa";
  }

  attribute def FlowRateValue {
    unit = "m^3/min";
  }

  attribute def VolumeValue :> volume {
    unit = "m^3";
  }

  attribute def MassRateValue {
    unit = "kg/min";
  }

  attribute def ConcentrationValue {
    unit = "kg/m^3";
  }

  attribute def DepthValue :> length {
    unit = "m";
  }

  attribute def TemperatureValue :> thermodynamicTemperature {
    unit = "degC";
  }

  attribute def PowerValue :> power {
    unit = "kW";
  }

  item def Water {
    attribute temperature : TemperatureValue;
    attribute dissolvedSolids : ConcentrationValue;
  }

  item def Proppant {
    attribute meshSize : Integer;
    attribute bulkDensity : ConcentrationValue;
  }

  item def ChemicalAdditive {
    attribute additiveType : String;
    attribute dosage : ConcentrationValue;
  }

  item def FracturingFluid {
    attribute pressure : PressureValue;
    attribute flowRate : FlowRateValue;
    attribute slurryDensity : ConcentrationValue;
    attribute proppantConcentration : ConcentrationValue;
    part carrierWater : Water;
    part suspendedProppant : Proppant;
    part additive : ChemicalAdditive[0..*];
  }

  item def ProducedFluid {
    attribute flowRate : FlowRateValue;
    attribute pressure : PressureValue;
    attribute hydrocarbonFraction : Real;
    attribute waterFraction : Real;
    attribute solidsConcentration : ConcentrationValue;
  }

  item def ControlSignal {
    attribute commandName : String;
    attribute targetValue : Real;
    attribute timestamp : String;
  }

  item def SensorReading {
    attribute measuredValue : Real;
    attribute unitSymbol : String;
    attribute timestamp : String;
    attribute valid : Boolean;
  }

  port def FluidInletPort {
    in item fluid : FracturingFluid;
    attribute ratedPressure : PressureValue;
    attribute ratedFlow : FlowRateValue;
  }

  port def FluidOutletPort {
    out item fluid : FracturingFluid;
    attribute ratedPressure : PressureValue;
    attribute ratedFlow : FlowRateValue;
  }

  port def ProducedFluidPort {
    out item producedFluid : ProducedFluid;
    attribute ratedFlow : FlowRateValue;
  }

  port def ControlInputPort {
    in item command : ControlSignal;
  }

  port def TelemetryOutputPort {
    out item reading : SensorReading;
  }

  port def PowerPort {
    in attribute electricalPower : PowerValue;
  }

  connection def FluidConnection {
    end source : FluidOutletPort;
    end target : FluidInletPort;
  }

  connection def ControlConnection {
    end controller : ControlInputPort;
    end controlledEquipment : ControlInputPort;
  }

  part def WaterStorageTank {
    attribute capacity : VolumeValue = 8000;
    attribute currentVolume : VolumeValue;
    port outlet : FluidOutletPort {
      attribute ratedPressure = 1;
      attribute ratedFlow = 12;
    }
    port levelTelemetry : TelemetryOutputPort;
  }

  part def ChemicalStorageUnit {
    attribute additiveCapacity : VolumeValue = 120;
    port outlet : FluidOutletPort {
      attribute ratedPressure = 1;
      attribute ratedFlow = 2;
    }
    port telemetry : TelemetryOutputPort;
  }

  part def ProppantSilo {
    attribute capacity : VolumeValue = 600;
    attribute remainingProppantMass : Real;
    port discharge : FluidOutletPort {
      attribute ratedPressure = 1;
      attribute ratedFlow = 8;
    }
    port telemetry : TelemetryOutputPort;
  }

  part def HydrationAndBlendingUnit {
    attribute maxBlendRate : FlowRateValue = 14;
    attribute targetProppantConcentration : ConcentrationValue;
    port waterInlet : FluidInletPort;
    port chemicalInlet : FluidInletPort;
    port proppantInlet : FluidInletPort;
    port slurryOutlet : FluidOutletPort {
      attribute ratedPressure = 3;
      attribute ratedFlow = 14;
    }
    port control : ControlInputPort;
    port telemetry : TelemetryOutputPort;
  }

  part def HighPressurePump {
    attribute maxDischargePressure : PressureValue = 85;
    attribute maxFlowRate : FlowRateValue = 4;
    attribute ratedPower : PowerValue = 2500;
    port suction : FluidInletPort;
    port discharge : FluidOutletPort {
      attribute ratedPressure = 85;
      attribute ratedFlow = 4;
    }
    port power : PowerPort;
    port control : ControlInputPort;
    port telemetry : TelemetryOutputPort;
  }

  part def PumpManifold {
    attribute maxOperatingPressure : PressureValue = 90;
    port inlet : FluidInletPort[1..12];
    port outlet : FluidOutletPort {
      attribute ratedPressure = 90;
      attribute ratedFlow = 48;
    }
    port telemetry : TelemetryOutputPort;
  }

  part def Wellhead {
    attribute pressureRating : PressureValue = 100;
    attribute surfacePressureLimit : PressureValue = 82;
    port treatmentInlet : FluidInletPort;
    port producedFluidOutlet : ProducedFluidPort;
    port telemetry : TelemetryOutputPort;
  }

  part def Casing {
    attribute innerDiameter : Real;
    attribute cementIntegrityIndex : Real;
    attribute measuredDepth : DepthValue;
  }

  part def PerforatedInterval {
    attribute topDepth : DepthValue;
    attribute bottomDepth : DepthValue;
    attribute perforationCount : Integer;
    attribute formationBreakdownPressure : PressureValue;
  }

  part def FractureNetwork {
    attribute estimatedHalfLength : DepthValue;
    attribute estimatedHeight : DepthValue;
    attribute conductivity : Real;
    attribute containedWithinTargetZone : Boolean;
  }

  part def SubsurfaceReservoir {
    attribute targetDepth : DepthValue = 3200;
    attribute porePressure : PressureValue = 42;
    attribute minimumHorizontalStress : PressureValue = 56;
    attribute maximumAllowableFracturePressure : PressureValue = 78;
    part casing : Casing;
    part interval : PerforatedInterval;
    part fractures : FractureNetwork;
    port treatmentInlet : FluidInletPort;
    port producedFluidOutlet : ProducedFluidPort;
  }

  part def FlowbackSeparator {
    attribute maxLiquidRate : FlowRateValue = 6;
    attribute maxGasRate : Real;
    port inlet : ProducedFluidPort;
    port waterOutlet : ProducedFluidPort;
    port hydrocarbonOutlet : ProducedFluidPort;
    port solidsOutlet : ProducedFluidPort;
    port telemetry : TelemetryOutputPort;
  }

  part def ClosedLoopControlSystem {
    attribute samplePeriod : Real = 0.5;
    attribute pressureSetpoint : PressureValue;
    attribute flowSetpoint : FlowRateValue;
    attribute emergencyShutdownEnabled : Boolean = true;
    port pressureTelemetry : TelemetryOutputPort[0..*];
    port flowTelemetry : TelemetryOutputPort[0..*];
    port pumpCommands : ControlInputPort[0..*];
    port blenderCommand : ControlInputPort;
    port wellheadCommand : ControlInputPort;
  }

  part def SafetyInterlockSystem {
    attribute highPressureTrip : PressureValue = 84;
    attribute lowSuctionPressureTrip : PressureValue = 0.2;
    attribute leakDetected : Boolean;
    attribute emergencyStopRequested : Boolean;
    port telemetryIn : TelemetryOutputPort[0..*];
    port shutdownCommand : ControlInputPort;
  }

  action def PrepareTreatment {
    out item readyCommand : ControlSignal;
  }

  action def BlendFracturingFluid {
    in item water : Water;
    in item proppant : Proppant;
    in item additive : ChemicalAdditive;
    out item slurry : FracturingFluid;
  }

  action def PressurizeAndInject {
    in item slurry : FracturingFluid;
    out item pressurizedSlurry : FracturingFluid;
  }

  action def CreateAndPropFractures {
    in item pressurizedSlurry : FracturingFluid;
    out item stimulatedReservoir : FractureNetwork;
  }

  action def FlowbackAndSeparate {
    in item reservoirFluid : ProducedFluid;
    out item recoveredWater : ProducedFluid;
    out item recoveredHydrocarbon : ProducedFluid;
  }

  state def FracturingJobStateMachine {
    state Idle;
    state SiteRigUp;
    state PressureTest;
    state PadInjection;
    state ProppantRamp;
    state Flush;
    state ShutIn;
    state Flowback;
    state Complete;
    state EmergencyShutdown;

    transition first Idle then SiteRigUp;
    transition SiteRigUp then PressureTest;
    transition PressureTest then PadInjection;
    transition PadInjection then ProppantRamp;
    transition ProppantRamp then Flush;
    transition Flush then ShutIn;
    transition ShutIn then Flowback;
    transition Flowback then Complete;

    transition Idle then EmergencyShutdown;
    transition SiteRigUp then EmergencyShutdown;
    transition PressureTest then EmergencyShutdown;
    transition PadInjection then EmergencyShutdown;
    transition ProppantRamp then EmergencyShutdown;
    transition Flush then EmergencyShutdown;
    transition ShutIn then EmergencyShutdown;
    transition Flowback then EmergencyShutdown;
  }

  part def HydraulicFracturingSystem {
    attribute primaryFunction : String =
      "Blend water, proppant, and additives into fracturing fluid; pump the fluid at controlled high pressure into a completed wellbore; create and prop conductive fractures in the target reservoir; and manage flowback while maintaining pressure, containment, and environmental safeguards.";

    attribute totalDesignedPumpRate : FlowRateValue = 36;
    attribute maximumSurfaceTreatingPressure : PressureValue = 82;
    attribute designedStageVolume : VolumeValue = 3500;
    attribute targetReservoirDepth : DepthValue = 3200;

    part waterStorage : WaterStorageTank;
    part chemicalStorage : ChemicalStorageUnit;
    part proppantStorage : ProppantSilo;
    part blender : HydrationAndBlendingUnit;
    part pump[9] : HighPressurePump;
    part manifold : PumpManifold;
    part wellhead : Wellhead;
    part reservoir : SubsurfaceReservoir;
    part separator : FlowbackSeparator;
    part controller : ClosedLoopControlSystem;
    part safety : SafetyInterlockSystem;
    part jobBehavior : FracturingJobStateMachine;

    connect waterStorage.outlet to blender.waterInlet;
    connect chemicalStorage.outlet to blender.chemicalInlet;
    connect proppantStorage.discharge to blender.proppantInlet;

    connect blender.slurryOutlet to pump.suction;
    connect pump.discharge to manifold.inlet;
    connect manifold.outlet to wellhead.treatmentInlet;
    connect wellhead.treatmentInlet to reservoir.treatmentInlet;
    connect reservoir.producedFluidOutlet to wellhead.producedFluidOutlet;
    connect wellhead.producedFluidOutlet to separator.inlet;

    connect waterStorage.levelTelemetry to controller.flowTelemetry;
    connect blender.telemetry to controller.flowTelemetry;
    connect pump.telemetry to controller.pressureTelemetry;
    connect manifold.telemetry to controller.pressureTelemetry;
    connect wellhead.telemetry to controller.pressureTelemetry;
    connect separator.telemetry to controller.flowTelemetry;

    connect controller.blenderCommand to blender.control;
    connect controller.pumpCommands to pump.control;
    connect controller.wellheadCommand to safety.shutdownCommand;
    connect safety.shutdownCommand to pump.control;
  }

  requirement def PrimaryFunctionRequirement {
    subject system : HydraulicFracturingSystem;
    require constraint {
      system.totalDesignedPumpRate >= 30 and
      system.maximumSurfaceTreatingPressure <= 82
    }
  }

  requirement def PressureContainmentRequirement {
    subject system : HydraulicFracturingSystem;
    require constraint {
      system.wellhead.pressureRating > system.maximumSurfaceTreatingPressure and
      system.manifold.maxOperatingPressure > system.maximumSurfaceTreatingPressure
    }
  }

  requirement def ReservoirProtectionRequirement {
    subject system : HydraulicFracturingSystem;
    require constraint {
      system.maximumSurfaceTreatingPressure <= system.reservoir.maximumAllowableFracturePressure and
      system.reservoir.fractures.containedWithinTargetZone == true
    }
  }

  requirement def BlendQualityRequirement {
    subject system : HydraulicFracturingSystem;
    require constraint {
      system.blender.maxBlendRate >= system.totalDesignedPumpRate / 3 and
      system.blender.targetProppantConcentration >= 0
    }
  }

  requirement def SafetyShutdownRequirement {
    subject system : HydraulicFracturingSystem;
    require constraint {
      system.safety.emergencyShutdownEnabled == true and
      system.safety.highPressureTrip > system.maximumSurfaceTreatingPressure
    }
  }

  requirement def ClosedLoopControlRequirement {
    subject system : HydraulicFracturingSystem;
    require constraint {
      system.controller.samplePeriod <= 1.0 and
      system.controller.emergencyShutdownEnabled == true
    }
  }

  requirement def FlowbackManagementRequirement {
    subject system : HydraulicFracturingSystem;
    require constraint {
      system.separator.maxLiquidRate >= 4
    }
  }

}

package LungFluteSystemModel {

    import ScalarValues::*;
    import ISQ::*;

    attribute def PressureValue :> Real {
        unit = "Pa";
    }

    attribute def FlowRateValue :> Real {
        unit = "L/min";
    }

    attribute def FrequencyValue :> Real {
        unit = "Hz";
    }

    attribute def SoundPressureLevelValue :> Real {
        unit = "dB";
    }

    attribute def TimeValue :> Real {
        unit = "s";
    }

    attribute def VolumeValue :> Real {
        unit = "mL";
    }

    attribute def LengthValue :> Real {
        unit = "mm";
    }

    attribute def PercentValue :> Real {
        unit = "%";
    }

    item def ExhaledAir {
        attribute pressure : PressureValue;
        attribute flowRate : FlowRateValue;
        attribute humidity : PercentValue;
        attribute temperature : Real;
    }

    item def OscillatoryPressureWave {
        attribute frequency : FrequencyValue;
        attribute peakToPeakPressure : PressureValue;
        attribute soundPressureLevel : SoundPressureLevelValue;
    }

    item def MobilizedSecretion {
        attribute volume : VolumeValue;
        attribute viscosity : Real;
        attribute clearanceReadiness : PercentValue;
    }

    item def UserInstruction {
        attribute inhalationDuration : TimeValue;
        attribute exhalationDuration : TimeValue;
        attribute treatmentCycles : Integer;
    }

    port def MouthPort {
        in item breathIn : ExhaledAir;
        out item acousticWaveOut : OscillatoryPressureWave;
    }

    port def AirwayInterfacePort {
        out item pressureWaveToAirway : OscillatoryPressureWave;
        in item mobilizedSecretionIn : MobilizedSecretion;
    }

    port def ExhaustPort {
        out item ventedAir : ExhaledAir;
    }

    port def GuidancePort {
        out item instruction : UserInstruction;
    }

    part def LungFluteDevice {
        attribute operatingFrequency : FrequencyValue = 16.0;
        attribute minimumExhalationFlow : FlowRateValue = 10.0;
        attribute nominalTreatmentDuration : TimeValue = 600.0;

        port mouthpiece : MouthPort;
        port airwayOutput : AirwayInterfacePort;
        port exhaust : ExhaustPort;
        port guidance : GuidancePort;

        part mouthpieceBody {
            attribute innerDiameter : LengthValue = 22.0;
            attribute length : LengthValue = 65.0;
        }

        part reedAssembly {
            attribute reedLength : LengthValue = 105.0;
            attribute reedWidth : LengthValue = 12.0;
            attribute naturalFrequency : FrequencyValue = 16.0;
            attribute pressureActivationThreshold : PressureValue = 120.0;
        }

        part resonatorChamber {
            attribute chamberLength : LengthValue = 140.0;
            attribute chamberVolume : VolumeValue = 180.0;
        }

        part exhaustVent {
            attribute ventArea : Real = 75.0;
        }

        part hygienicBarrier {
            attribute singlePatientUse : Boolean = true;
            attribute secretionIngressReduction : PercentValue = 95.0;
        }

        connect mouthpiece.acousticWaveOut to airwayOutput.pressureWaveToAirway;
        connect mouthpiece.breathIn to exhaust.ventedAir;
    }

    part def PatientRespiratorySystem {
        port oralInterface : MouthPort;
        port bronchialAirway : AirwayInterfacePort;

        part upperAirway {
            attribute airwayResistance : Real = 2.0;
        }

        part bronchialTree {
            attribute mucusAdhesionLevel : PercentValue = 70.0;
            attribute secretionVolume : VolumeValue = 20.0;
            attribute ciliaryTransportEffectiveness : PercentValue = 45.0;
        }

        part lungs {
            attribute exhalationCapacity : VolumeValue = 2500.0;
            attribute targetExhalationFlow : FlowRateValue = 15.0;
        }

        connect oralInterface.acousticWaveOut to bronchialAirway.pressureWaveToAirway;
        connect bronchialAirway.mobilizedSecretionIn to oralInterface.breathIn;
    }

    part def TreatmentSession {
        attribute prescribedCycles : Integer = 20;
        attribute restInterval : TimeValue = 5.0;
        attribute totalDuration : TimeValue = 600.0;

        part device : LungFluteDevice;
        part patient : PatientRespiratorySystem;

        connect patient.oralInterface to device.mouthpiece;
        connect device.airwayOutput to patient.bronchialAirway;
    }

    action def GenerateOscillatoryPressure {
        in item exhaledAir : ExhaledAir;
        out item pressureWave : OscillatoryPressureWave;

        attribute requiredFlow : FlowRateValue = 10.0;
        attribute generatedFrequency : FrequencyValue = 16.0;
        attribute generatedPeakToPeakPressure : PressureValue = 250.0;
    }

    action def MobilizeBronchialSecretions {
        in item pressureWave : OscillatoryPressureWave;
        out item secretion : MobilizedSecretion;

        attribute minimumEffectiveFrequency : FrequencyValue = 12.0;
        attribute maximumEffectiveFrequency : FrequencyValue = 22.0;
        attribute targetClearanceReadiness : PercentValue = 80.0;
    }

    action def ConductTherapyCycle {
        in item userBreath : ExhaledAir;
        out item mobilizedMucus : MobilizedSecretion;

        first start;
        then generate : GenerateOscillatoryPressure;
        then mobilize : MobilizeBronchialSecretions;
        then complete;

        flow userBreath to generate.exhaledAir;
        flow generate.pressureWave to mobilize.pressureWave;
        flow mobilize.secretion to mobilizedMucus;
    }

    action def PerformTreatmentSession {
        attribute cycleCount : Integer = 20;
        attribute sessionDuration : TimeValue = 600.0;

        action instructPatient {
            out item instruction : UserInstruction;
        }

        action repeatCycles : ConductTherapyCycle;

        action coughAndClear {
            in item mobilizedMucus : MobilizedSecretion;
        }

        first instructPatient;
        then repeatCycles;
        then coughAndClear;
    }

    state def LungFluteOperatingState {
        entry action initializeDevice;

        state Idle;
        state AwaitingExhalation;
        state ReedOscillating;
        state DeliveringAcousticWave;
        state CycleComplete;
        state SessionComplete;

        transition initial then Idle;

        transition Idle
            first AwaitingExhalation
            accept StartTreatment;

        transition AwaitingExhalation
            first ReedOscillating
            accept ExhalationDetected
            if exhaledFlow >= 10.0;

        transition ReedOscillating
            first DeliveringAcousticWave
            accept StableOscillation
            if oscillationFrequency >= 12.0 and oscillationFrequency <= 22.0;

        transition DeliveringAcousticWave
            first CycleComplete
            accept ExhalationEnded;

        transition CycleComplete
            first AwaitingExhalation
            accept ContinueTreatment
            if completedCycles < prescribedCycles;

        transition CycleComplete
            first SessionComplete
            accept EndTreatment
            if completedCycles >= prescribedCycles;
    }

    requirement def PrimaryFunctionRequirement {
        doc /* The system shall convert patient exhalation through a reed-based acoustic chamber into low-frequency oscillatory pressure waves that travel into the bronchial airways to loosen, mobilize, and support clearance of mucus secretions. */
    }

    requirement def OscillationFrequencyRequirement {
        attribute minFrequency : FrequencyValue = 12.0;
        attribute maxFrequency : FrequencyValue = 22.0;

        require constraint {
            pressureWave.frequency >= minFrequency and pressureWave.frequency <= maxFrequency
        }
    }

    requirement def ExhalationFlowRequirement {
        attribute minimumFlow : FlowRateValue = 10.0;

        require constraint {
            exhaledAir.flowRate >= minimumFlow
        }
    }

    requirement def PressureWaveRequirement {
        attribute minimumPeakToPeakPressure : PressureValue = 150.0;
        attribute maximumPeakToPeakPressure : PressureValue = 500.0;

        require constraint {
            pressureWave.peakToPeakPressure >= minimumPeakToPeakPressure and
            pressureWave.peakToPeakPressure <= maximumPeakToPeakPressure
        }
    }

    requirement def TreatmentCycleRequirement {
        attribute minimumCycles : Integer = 10;
        attribute nominalCycles : Integer = 20;

        require constraint {
            treatmentSession.prescribedCycles >= minimumCycles and
            treatmentSession.prescribedCycles <= nominalCycles
        }
    }

    requirement def HygieneRequirement {
        attribute minimumIngressReduction : PercentValue = 90.0;

        require constraint {
            device.hygienicBarrier.secretionIngressReduction >= minimumIngressReduction
        }
    }

    requirement def UsabilityRequirement {
        attribute maximumSessionDuration : TimeValue = 900.0;

        require constraint {
            treatmentSession.totalDuration <= maximumSessionDuration
        }
    }

    satisfy PrimaryFunctionRequirement by LungFluteDevice;
    satisfy OscillationFrequencyRequirement by LungFluteDevice::reedAssembly;
    satisfy ExhalationFlowRequirement by PatientRespiratorySystem::lungs;
    satisfy PressureWaveRequirement by LungFluteDevice::reedAssembly;
    satisfy TreatmentCycleRequirement by TreatmentSession;
    satisfy HygieneRequirement by LungFluteDevice::hygienicBarrier;
    satisfy UsabilityRequirement by TreatmentSession;

    part lungFluteTherapySystem : TreatmentSession {
        attribute primaryFunction : String =
            "Provide non-pharmacologic airway clearance by using exhaled breath to vibrate an internal reed, producing low-frequency acoustic pressure waves that propagate into the lungs and help mobilize bronchial mucus for coughing and expectoration.";

        perform action sessionBehavior : PerformTreatmentSession;

        exhibit state operatingState : LungFluteOperatingState;
    }

}

package RudderSystemModel {
    import ScalarValues::*;

    attribute def Angle :> Real { :>> unit = "deg"; }
    attribute def AngularRate :> Real { :>> unit = "deg/s"; }
    attribute def Torque :> Real { :>> unit = "N*m"; }
    attribute def Force :> Real { :>> unit = "N"; }
    attribute def Pressure :> Real { :>> unit = "Pa"; }
    attribute def Length :> Real { :>> unit = "m"; }
    attribute def Area :> Real { :>> unit = "m^2"; }
    attribute def Voltage :> Real { :>> unit = "V"; }
    attribute def Current :> Real { :>> unit = "A"; }
    attribute def Time :> Real { :>> unit = "s"; }

    enum def RudderMode {
        enum idle;
        enum manual;
        enum automatic;
        enum emergencyCentering;
        enum failed;
    }

    enum def RudderHealth {
        enum nominal;
        enum degraded;
        enum faulted;
    }

    item def SteeringCommand {
        attribute targetAngle : Angle;
        attribute commandedRate : AngularRate;
        attribute mode : RudderMode;
    }

    item def RudderFeedback {
        attribute actualAngle : Angle;
        attribute actualRate : AngularRate;
        attribute hydraulicPressure : Pressure;
        attribute health : RudderHealth;
    }

    item def ElectricalPower {
        attribute voltage : Voltage;
        attribute current : Current;
    }

    item def HydraulicPower {
        attribute supplyPressure : Pressure;
        attribute returnPressure : Pressure;
        attribute availableForce : Force;
    }

    item def HydrodynamicLoad {
        attribute lateralForce : Force;
        attribute hingeTorque : Torque;
        attribute flowPressure : Pressure;
    }

    port def CommandInputPort {
        in item command : SteeringCommand;
    }

    port def FeedbackOutputPort {
        out item feedback : RudderFeedback;
    }

    port def ElectricalPowerPort {
        in item power : ElectricalPower;
    }

    port def HydraulicPowerPort {
        in item hydraulicPower : HydraulicPower;
    }

    port def MechanicalRotationPort {
        in item appliedTorque : Torque;
        out item measuredAngle : Angle;
    }

    port def WaterLoadPort {
        in item waterLoad : HydrodynamicLoad;
        out item steeringForce : Force;
    }

    part def HelmInterface {
        port commandOut : CommandInputPort;
        attribute requestedAngle : Angle;
        attribute requestedRate : AngularRate;
    }

    part def RudderController {
        port commandIn : CommandInputPort;
        port feedbackIn : FeedbackOutputPort;
        port actuatorCommandOut : CommandInputPort;

        attribute commandedAngle : Angle;
        attribute angleError : Angle;
        attribute activeMode : RudderMode;
        attribute health : RudderHealth;
        attribute maxAllowedAngle : Angle = 35.0;
        attribute maxAllowedRate : AngularRate = 8.0;
    }

    part def PowerUnit {
        port electricalIn : ElectricalPowerPort;
        port hydraulicOut : HydraulicPowerPort;

        attribute nominalVoltage : Voltage = 440.0;
        attribute nominalPressure : Pressure = 16000000.0;
        attribute minimumOperatingPressure : Pressure = 9000000.0;
    }

    part def SteeringActuator {
        port commandIn : CommandInputPort;
        port hydraulicIn : HydraulicPowerPort;
        port rotationOut : MechanicalRotationPort;

        attribute actuatorStroke : Length = 0.75;
        attribute maximumTorque : Torque = 95000.0;
        attribute responseTime : Time = 4.0;
    }

    part def RudderStock {
        port actuatorSide : MechanicalRotationPort;
        port bladeSide : MechanicalRotationPort;

        attribute diameter : Length = 0.32;
        attribute allowableTorque : Torque = 120000.0;
        attribute currentTorque : Torque;
    }

    part def RudderBlade {
        port shaftInput : MechanicalRotationPort;
        port waterInterface : WaterLoadPort;

        attribute angle : Angle;
        attribute area : Area = 9.5;
        attribute span : Length = 3.8;
        attribute chord : Length = 2.5;
        attribute maximumDeflection : Angle = 35.0;
        attribute generatedLateralForce : Force;
    }

    part def AngleSensor {
        port measuredRotation : MechanicalRotationPort;
        port feedbackOut : FeedbackOutputPort;

        attribute measuredAngle : Angle;
        attribute measuredRate : AngularRate;
        attribute accuracy : Angle = 0.25;
    }

    part def VesselHullInterface {
        port waterLoad : WaterLoadPort;

        attribute localFlowPressure : Pressure;
        attribute transmittedSteeringForce : Force;
    }

    action def LimitRudderCommand {
        in item rawCommand : SteeringCommand;
        out item limitedCommand : SteeringCommand;

        assert constraint angleWithinLimits {
            limitedCommand.targetAngle <= 35.0 and limitedCommand.targetAngle >= -35.0
        }

        assert constraint rateWithinLimits {
            limitedCommand.commandedRate <= 8.0 and limitedCommand.commandedRate >= 0.0
        }
    }

    action def RotateRudderBlade {
        in item command : SteeringCommand;
        in item hydraulicPower : HydraulicPower;
        out item feedback : RudderFeedback;

        assert constraint pressureAvailable {
            hydraulicPower.supplyPressure >= 9000000.0
        }
    }

    action def GenerateSteeringForce {
        in item bladeAngle : Angle;
        in item waterLoad : HydrodynamicLoad;
        out item lateralForce : Force;
    }

    state def RudderOperatingStateMachine {
        entry action initialize {
            activeMode = RudderMode::idle;
        }

        state Idle;
        state ManualControl;
        state AutomaticControl;
        state HoldingAngle;
        state EmergencyCentering;
        state Faulted;

        transition first Idle;

        transition Idle to ManualControl
            accept SteeringCommand
            if command.mode == RudderMode::manual;

        transition Idle to AutomaticControl
            accept SteeringCommand
            if command.mode == RudderMode::automatic;

        transition ManualControl to HoldingAngle
            if angleError <= 0.5 and angleError >= -0.5;

        transition AutomaticControl to HoldingAngle
            if angleError <= 0.5 and angleError >= -0.5;

        transition HoldingAngle to ManualControl
            accept SteeringCommand
            if command.mode == RudderMode::manual;

        transition HoldingAngle to AutomaticControl
            accept SteeringCommand
            if command.mode == RudderMode::automatic;

        transition ManualControl to EmergencyCentering
            accept SteeringCommand
            if command.mode == RudderMode::emergencyCentering;

        transition AutomaticControl to EmergencyCentering
            accept SteeringCommand
            if command.mode == RudderMode::emergencyCentering;

        transition EmergencyCentering to Idle
            if angleError <= 0.5 and angleError >= -0.5;

        transition Idle to Faulted if health == RudderHealth::faulted;
        transition ManualControl to Faulted if health == RudderHealth::faulted;
        transition AutomaticControl to Faulted if health == RudderHealth::faulted;
        transition HoldingAngle to Faulted if health == RudderHealth::faulted;
        transition EmergencyCentering to Faulted if health == RudderHealth::faulted;
    }

    part def RudderSystem {
        part helm : HelmInterface;
        part controller : RudderController;
        part powerUnit : PowerUnit;
        part actuator : SteeringActuator;
        part stock : RudderStock;
        part blade : RudderBlade;
        part angleSensor : AngleSensor;
        part hullInterface : VesselHullInterface;

        port commandInput : CommandInputPort;
        port feedbackOutput : FeedbackOutputPort;
        port electricalPowerInput : ElectricalPowerPort;
        port waterLoadInput : WaterLoadPort;

        attribute totalRudderAngle : Angle;
        attribute primaryFunctionDescription : String =
            "Convert steering commands into controlled rudder blade rotation, producing hydrodynamic lateral force that changes vessel heading.";

        connection commandInput to helm.commandOut;
        connection helm.commandOut to controller.commandIn;
        connection controller.actuatorCommandOut to actuator.commandIn;
        connection electricalPowerInput to powerUnit.electricalIn;
        connection powerUnit.hydraulicOut to actuator.hydraulicIn;
        connection actuator.rotationOut to stock.actuatorSide;
        connection stock.bladeSide to blade.shaftInput;
        connection blade.waterInterface to hullInterface.waterLoad;
        connection waterLoadInput to blade.waterInterface;
        connection stock.bladeSide to angleSensor.measuredRotation;
        connection angleSensor.feedbackOut to controller.feedbackIn;
        connection angleSensor.feedbackOut to feedbackOutput;

        perform action limitCommand : LimitRudderCommand;
        perform action rotateBlade : RotateRudderBlade;
        perform action createSteeringForce : GenerateSteeringForce;

        exhibit state behavior : RudderOperatingStateMachine;
    }

    requirement def PrimaryRudderFunctionRequirement {
        subject rudderSystem : RudderSystem;

        doc /* The rudder system shall provide the primary high-level function of steering a vessel by rotating a submerged rudder blade about a vertical stock in response to helm or automatic steering commands. */

        require constraint controlledDeflection {
            rudderSystem.blade.angle <= rudderSystem.blade.maximumDeflection and
            rudderSystem.blade.angle >= -rudderSystem.blade.maximumDeflection
        }

        require constraint producesSteeringForce {
            rudderSystem.blade.generatedLateralForce != 0.0
        }
    }

    requirement def RudderAngleLimitRequirement {
        subject rudderSystem : RudderSystem;

        require constraint angleLimit {
            rudderSystem.blade.angle <= 35.0 and rudderSystem.blade.angle >= -35.0
        }
    }

    requirement def RudderResponseRequirement {
        subject rudderSystem : RudderSystem;

        require constraint responseTime {
            rudderSystem.actuator.responseTime <= 4.0
        }
    }

    requirement def RudderFeedbackRequirement {
        subject rudderSystem : RudderSystem;

        require constraint sensorAccuracy {
            rudderSystem.angleSensor.accuracy <= 0.25
        }
    }

    requirement def RudderStructuralRequirement {
        subject rudderSystem : RudderSystem;

        require constraint torqueCapacity {
            rudderSystem.stock.allowableTorque >= rudderSystem.stock.currentTorque
        }
    }

    part rudderSystem : RudderSystem;

    satisfy PrimaryRudderFunctionRequirement by rudderSystem;
    satisfy RudderAngleLimitRequirement by rudderSystem;
    satisfy RudderResponseRequirement by rudderSystem;
    satisfy RudderFeedbackRequirement by rudderSystem;
    satisfy RudderStructuralRequirement by rudderSystem;
}

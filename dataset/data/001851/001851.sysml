package 'Rudder System' {
	private import ScalarValues::*;
	private import ISQ::*;
	private import SI::*;
	
	attribute def RudderAngle :> ISQ::PlaneAngleValue {
		doc /* Angular deflection of the rudder from neutral centerline position */
	}
	
	attribute def YawMoment :> ISQ::TorqueValue {
		doc /* Yawing moment generated by rudder deflection */
	}
	
	attribute def FluidVelocity :> ISQ::SpeedValue {
		doc /* Velocity of fluid flow over the rudder surface */
	}
	
	attribute def SteeringInput :> ISQ::PlaneAngleValue {
		doc /* Commanded rudder angle from operator or autopilot */
	}
	
	attribute def HydraulicPressure :> ISQ::PressureValue {
		doc /* Operating pressure of hydraulic actuation system */
	}
	
	attribute def LateralForce :> ISQ::ForceValue {
		doc /* Lateral force generated by rudder in fluid stream */
	}
	
	port def HydraulicSupplyPort {
		in pressure : HydraulicPressure;
		attribute flowRate : ISQ::VolumeFlowRateValue;
	}
	
	port def CommandInputPort {
		in commandedAngle : SteeringInput;
	}
	
	port def PositionFeedbackPort {
		out actualAngle : RudderAngle;
	}
	
	port def FluidDynamicPort {
		in fluidVelocity : FluidVelocity;
		out generatedForce : LateralForce;
		out generatedMoment : YawMoment;
	}
	
	item def RudderBlade {
		doc /* Primary control surface that deflects fluid flow to generate directional control forces */
		
		attribute surfaceArea : ISQ::AreaValue;
		attribute aspectRatio : Real;
		attribute maxDeflectionAngle : RudderAngle;
		attribute currentAngle : RudderAngle;
		
		port fluidPort : FluidDynamicPort;
	}
	
	item def HydraulicActuator {
		doc /* Hydraulic cylinder and linkage that positions the rudder blade */
		
		attribute strokeLength : ISQ::LengthValue;
		attribute maxForce : ISQ::ForceValue;
		attribute actuationRate : ISQ::AngularVelocityValue;
		
		port hydraulicPort : HydraulicSupplyPort;
		port commandPort : CommandInputPort;
		port feedbackPort : PositionFeedbackPort;
	}
	
	item def AngleSensor {
		doc /* Measures actual rudder deflection angle for feedback control */
		
		attribute resolution : RudderAngle;
		attribute accuracy : RudderAngle;
		
		port sensorOutput : PositionFeedbackPort;
	}
	
	item def SteeringMechanism {
		doc /* Operator interface for commanding rudder deflection */
		
		attribute mechanicalAdvantage : Real;
		
		port steeringOutput : CommandInputPort;
	}
	
	action def GenerateDirectionalForce {
		doc /* Calculate lateral force and yawing moment from rudder deflection and fluid velocity */
		
		in deflectionAngle : RudderAngle;
		in velocity : FluidVelocity;
		in area : ISQ::AreaValue;
		out lateralForce : LateralForce;
		out yawMoment : YawMoment;
	}
	
	action def PositionRudder {
		doc /* Actuate rudder to commanded angle using hydraulic power */
		
		in commandAngle : RudderAngle;
		in currentAngle : RudderAngle;
		in hydraulicPressure : HydraulicPressure;
		out targetAngle : RudderAngle;
		out positionError : RudderAngle;
		out actuationComplete : Boolean;
	}
	
	action def ProvideDirectionalControl {
		doc /* High-level action coordinating rudder operation to control vehicle heading */
		
		in steeringCommand : SteeringInput;
		in fluidSpeed : FluidVelocity;
		out controlMoment : YawMoment;
		
		first start;
		then action interpretCommand {
			in cmd = steeringCommand;
			out desiredAngle : RudderAngle;
		}
		then action positionControl : PositionRudder {
			in commandAngle = interpretCommand.desiredAngle;
			in currentAngle;
			in hydraulicPressure;
			out targetAngle;
			out positionError;
			out actuationComplete;
		}
		then action forceGeneration : GenerateDirectionalForce {
			in deflectionAngle = positionControl.targetAngle;
			in velocity = fluidSpeed;
			in area;
			out lateralForce;
			out yawMoment;
		}
		then assign controlMoment := forceGeneration.yawMoment;
		then done;
	}
	
	attribute def SteeringCommandReceived;
	attribute def TargetPositionReached;
	attribute def NewSteeringCommand;
	attribute def CenteringCommand;
	attribute def SystemFailure;
	
	state def RudderOperationalMode {
		doc /* State machine representing operational modes of the rudder system */
		
		entry; then neutral;
		
		state neutral {
			doc /* Rudder centered at zero deflection */
			entry action centerRudder;
		}
		
		state deflecting {
			doc /* Rudder actively moving to commanded position */
			entry action beginActuation;
			do action maintainActuation;
			exit action completeActuation;
		}
		
		state holding {
			doc /* Rudder maintaining steady deflection angle */
			do action holdPosition;
		}
		
		state emergency {
			doc /* Emergency mode with rudder locked or centered */
			entry action activateEmergencyMode;
		}
		
		transition neutral_to_deflecting
			first neutral
			accept steeringCommandReceived : SteeringCommandReceived
			then deflecting;
		
		transition deflecting_to_holding
			first deflecting
			accept targetPositionReached : TargetPositionReached
			then holding;
		
		transition holding_to_deflecting
			first holding
			accept newSteeringCommand : NewSteeringCommand
			then deflecting;
		
		transition holding_to_neutral
			first holding
			accept centeringCommand : CenteringCommand
			then neutral;
		
		transition deflecting_to_neutral
			first deflecting
			accept centeringCommand2 : CenteringCommand
			then neutral;
		
		transition any_to_emergency
			first neutral
			accept systemFailure : SystemFailure
			then emergency;
	}
	
	part def RudderSystem {
		doc /* Integrated rudder system for vehicle directional control */
		
		part rudderBlade : RudderBlade;
		part actuator : HydraulicActuator;
		part angleSensor : AngleSensor;
		part steeringMechanism : SteeringMechanism;
		part hydraulicPowerUnit;
	}
	
	requirement def DirectionalControlCapability {
		doc /* The rudder system shall provide directional control by generating yawing moments */
		
		subject rudderSystem : RudderSystem;
		
		require constraint {
			doc /* Rudder shall generate sufficient yawing moment for directional control */
			rudderSystem.rudderBlade.fluidPort.generatedMoment >= 1000.0[SI::N*SI::m]
		}
	}
	
	requirement def AngleAccuracyRequirement {
		doc /* Rudder shall achieve commanded angle within specified tolerance */
		
		subject actuator : HydraulicActuator;
		
		require constraint {
			doc /* Position error shall not exceed 0.5 degrees */
			(actuator.commandPort.commandedAngle - actuator.feedbackPort.actualAngle) <= 0.5[SI::degree] and
			(actuator.commandPort.commandedAngle - actuator.feedbackPort.actualAngle) >= -0.5[SI::degree]
		}
	}
	
	requirement def ResponseTimeRequirement {
		doc /* Rudder shall respond to commands within specified time */
		
		subject actuator : HydraulicActuator;
		
		require constraint {
			doc /* Actuator shall achieve 20 degrees per second minimum rate */
			actuator.actuationRate >= 20.0[SI::degree/SI::s]
		}
	}
	
	requirement def DeflectionLimitRequirement {
		doc /* Rudder deflection shall remain within structural limits */
		
		subject blade : RudderBlade;
		
		require constraint {
			doc /* Rudder deflection shall not exceed maximum design angle */
			blade.currentAngle <= blade.maxDeflectionAngle and
			blade.currentAngle >= -blade.maxDeflectionAngle
		}
	}
	
	part rudderSystem : RudderSystem {
		doc /* Complete rudder system providing directional control for marine or aerospace vehicles */
		
		attribute nominalHydraulicPressure : HydraulicPressure = 3000.0[SI::psi];
		attribute maxRudderDeflection : RudderAngle = 35.0[SI::degree];
		attribute operatingFluidVelocity : FluidVelocity = 15.0[SI::m/SI::s];
		
		part redefines rudderBlade : RudderBlade {
			attribute :>> surfaceArea = 3.2[SI::m^2];
			attribute :>> aspectRatio = 1.8;
			attribute :>> maxDeflectionAngle = rudderSystem.maxRudderDeflection;
			attribute :>> currentAngle = 0.0[SI::degree];
		}
		
		part redefines actuator : HydraulicActuator {
			attribute :>> strokeLength = 0.6[SI::m];
			attribute :>> maxForce = 50000.0[SI::N];
			attribute :>> actuationRate = 25.0[SI::degree/SI::s];
		}
		
		part redefines angleSensor : AngleSensor {
			attribute :>> resolution = 0.1[SI::degree];
			attribute :>> accuracy = 0.2[SI::degree];
		}
		
		part redefines steeringMechanism : SteeringMechanism {
			attribute :>> mechanicalAdvantage = 4.0;
		}
		
		part redefines hydraulicPowerUnit {
			doc /* Provides pressurized hydraulic fluid to actuator */
			attribute systemPressure : HydraulicPressure = nominalHydraulicPressure;
			attribute reservoirCapacity : ISQ::VolumeValue = 50.0[SI::L];
		}
		
		connection steeringToActuator : CommandConnection
			connect steeringMechanism.steeringOutput to actuator.commandPort;
		
		connection hydraulicToActuator : HydraulicConnection
			connect hydraulicPowerUnit to actuator.hydraulicPort;
		
		connection sensorToActuator : FeedbackConnection
			connect angleSensor.sensorOutput to actuator.feedbackPort;
		
		connection actuatorToBlade : MechanicalLinkage
			connect actuator to rudderBlade;
		
		perform action directionalControl : ProvideDirectionalControl {
			in steeringCommand;
			in fluidSpeed = operatingFluidVelocity;
			out controlMoment;
		}
		
		exhibit state operationalMode : RudderOperationalMode;
		
		satisfy req1 : DirectionalControlCapability;
		satisfy req2 : AngleAccuracyRequirement;
		satisfy req3 : ResponseTimeRequirement;
		satisfy req4 : DeflectionLimitRequirement;
	}
	
	connection def CommandConnection {
		end source : CommandInputPort;
		end target : CommandInputPort;
	}
	
	connection def HydraulicConnection {
		doc /* Hydraulic fluid supply connection */
		end source;
		end target : HydraulicSupplyPort;
	}
	
	connection def FeedbackConnection {
		end source : PositionFeedbackPort;
		end target : PositionFeedbackPort;
	}
	
	connection def MechanicalLinkage {
		doc /* Mechanical connection transmitting motion from actuator to rudder blade */
		end actuatorEnd;
		end bladeEnd;
	}
}

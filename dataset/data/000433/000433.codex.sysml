package CochlearImplantModel {

    import ScalarValues::*;
    import ISQ::*;
    import SI::*;

    value def SoundPressure :> Real {
        unit = "Pa";
    }

    value def SoundPressureLevel :> Real {
        unit = "dB SPL";
    }

    value def Frequency :> Real {
        unit = "Hz";
    }

    value def TimeDuration :> Real {
        unit = "s";
    }

    value def Voltage :> Real {
        unit = "V";
    }

    value def Current :> Real {
        unit = "uA";
    }

    value def Charge :> Real {
        unit = "nC";
    }

    value def Impedance :> Real {
        unit = "Ohm";
    }

    value def DataRate :> Real {
        unit = "kbps";
    }

    value def BatteryCapacity :> Real {
        unit = "mAh";
    }

    enum def ImplantOperatingMode {
        enum off;
        enum standby;
        enum listening;
        enum stimulating;
        enum fault;
    }

    enum def ElectrodeContactState {
        enum inactive;
        enum cathodicPhase;
        enum interphaseGap;
        enum anodicPhase;
        enum telemetryMeasurement;
    }

    item def AcousticWave {
        attribute pressure : SoundPressure;
        attribute level : SoundPressureLevel;
        attribute frequency : Frequency;
        attribute duration : TimeDuration;
    }

    item def MicrophoneSignal {
        attribute voltage : Voltage;
        attribute sampleRate : Frequency;
        attribute dynamicRange : SoundPressureLevel;
    }

    item def DigitalAudioFrame {
        attribute frameDuration : TimeDuration;
        attribute sampleRate : Frequency;
        attribute channelCount : Integer;
        attribute encodedLevel : Real;
    }

    item def StimulationCommand {
        attribute electrodeIndex : Integer;
        attribute pulseAmplitude : Current;
        attribute pulseWidth : TimeDuration;
        attribute pulseRate : Frequency;
        attribute chargePerPhase : Charge;
    }

    item def BiphasicPulse {
        attribute amplitude : Current;
        attribute cathodicWidth : TimeDuration;
        attribute anodicWidth : TimeDuration;
        attribute interphaseGap : TimeDuration;
        attribute deliveredCharge : Charge;
    }

    item def NeuralExcitation {
        attribute cochlearRegionFrequency : Frequency;
        attribute excitationStrength : Real;
        attribute latency : TimeDuration;
    }

    item def TelemetryPacket {
        attribute linkRate : DataRate;
        attribute electrodeImpedance : Impedance;
        attribute batteryVoltage : Voltage;
        attribute processorTemperature : Real;
    }

    port def AcousticInputPort {
        in item sound : AcousticWave;
    }

    port def ElectricalSignalPort {
        in item inputSignal : MicrophoneSignal;
        out item outputSignal : MicrophoneSignal;
    }

    port def DigitalAudioPort {
        in item audioIn : DigitalAudioFrame;
        out item audioOut : DigitalAudioFrame;
    }

    port def RadioFrequencyPort {
        in item receivedCommand : StimulationCommand;
        out item transmittedCommand : StimulationCommand;
        in item receivedTelemetry : TelemetryPacket;
        out item transmittedTelemetry : TelemetryPacket;
    }

    port def StimulationPort {
        in item command : StimulationCommand;
        out item pulse : BiphasicPulse;
    }

    port def NeuralInterfacePort {
        out item excitation : NeuralExcitation;
    }

    port def PowerPort {
        in attribute supplyVoltage : Voltage;
        out attribute consumedCurrent : Current;
    }

    action def CaptureSound {
        in item acousticInput : AcousticWave;
        out item microphoneOutput : MicrophoneSignal;

        attribute minimumInputLevel : SoundPressureLevel = 25.0;
        attribute maximumInputLevel : SoundPressureLevel = 100.0;
        attribute nominalSampleRate : Frequency = 16000.0;
    }

    action def ProcessSound {
        in item microphoneInput : MicrophoneSignal;
        out item audioFrame : DigitalAudioFrame;

        attribute filterBankChannels : Integer = 22;
        attribute frameDuration : TimeDuration = 0.008;
        attribute compressionEnabled : Boolean = true;
    }

    action def EncodeStimulationPattern {
        in item audioFrame : DigitalAudioFrame;
        out item command : StimulationCommand;

        attribute minimumPulseWidth : TimeDuration = 0.000025;
        attribute maximumPulseWidth : TimeDuration = 0.000100;
        attribute maximumAmplitude : Current = 900.0;
    }

    action def TransmitAcrossSkin {
        in item externalCommand : StimulationCommand;
        out item implantedCommand : StimulationCommand;
        out item telemetry : TelemetryPacket;

        attribute carrierFrequency : Frequency = 5000000.0;
        attribute nominalDataRate : DataRate = 250.0;
    }

    action def GenerateBiphasicPulse {
        in item command : StimulationCommand;
        out item pulse : BiphasicPulse;

        attribute chargeBalanced : Boolean = true;
        attribute complianceVoltage : Voltage = 12.0;
    }

    action def StimulateAuditoryNerve {
        in item pulse : BiphasicPulse;
        out item neuralResponse : NeuralExcitation;

        attribute targetStructure : String = "spiral ganglion neurons";
    }

    state def ImplantLifecycle {
        entry;
        state Off;
        state Standby;
        state Listening;
        state Stimulating;
        state Fault;

        transition initial then Off;

        transition PowerApplied
            first Off
            then Standby;

        transition ValidAcousticInputDetected
            first Standby
            then Listening;

        transition StimulationFrameReady
            first Listening
            then Stimulating;

        transition FrameDelivered
            first Stimulating
            then Listening;

        transition NoInputTimeout
            first Listening
            then Standby;

        transition SafetyLimitExceeded
            first Standby
            then Fault;

        transition SafetyLimitExceeded
            first Listening
            then Fault;

        transition SafetyLimitExceeded
            first Stimulating
            then Fault;

        transition ResetCommanded
            first Fault
            then Standby;
    }

    state def ElectrodePulseLifecycle {
        entry;
        state Inactive;
        state CathodicPhase;
        state InterphaseGap;
        state AnodicPhase;
        state TelemetryMeasurement;

        transition initial then Inactive;

        transition PulseCommandReceived
            first Inactive
            then CathodicPhase;

        transition CathodicPhaseComplete
            first CathodicPhase
            then InterphaseGap;

        transition GapElapsed
            first InterphaseGap
            then AnodicPhase;

        transition AnodicPhaseComplete
            first AnodicPhase
            then TelemetryMeasurement;

        transition MeasurementComplete
            first TelemetryMeasurement
            then Inactive;
    }

    part def ExternalSoundProcessor {
        port acousticInput : AcousticInputPort;
        port microphoneOutput : ElectricalSignalPort;
        port digitalAudio : DigitalAudioPort;
        port rfLink : RadioFrequencyPort;
        port power : PowerPort;

        attribute microphoneSensitivity : Voltage = 0.010;
        attribute processorClock : Frequency = 48000000.0;
        attribute batteryCapacity : BatteryCapacity = 120.0;
        attribute operatingMode : ImplantOperatingMode = ImplantOperatingMode::standby;

        perform action capture : CaptureSound;
        perform action process : ProcessSound;
        perform action encode : EncodeStimulationPattern;
    }

    part def MicrophoneArray {
        port acousticInput : AcousticInputPort;
        port signalOutput : ElectricalSignalPort;

        attribute microphoneCount : Integer = 2;
        attribute inputNoiseLevel : SoundPressureLevel = 22.0;
        attribute maximumInputLevel : SoundPressureLevel = 105.0;
    }

    part def SpeechProcessor {
        port signalInput : ElectricalSignalPort;
        port audioOutput : DigitalAudioPort;

        attribute analysisChannels : Integer = 22;
        attribute lowFrequencyLimit : Frequency = 188.0;
        attribute highFrequencyLimit : Frequency = 7938.0;
        attribute frameDuration : TimeDuration = 0.008;
    }

    part def ExternalTransmitterCoil {
        port digitalInput : DigitalAudioPort;
        port rfOutput : RadioFrequencyPort;
        port power : PowerPort;

        attribute carrierFrequency : Frequency = 5000000.0;
        attribute telemetryEnabled : Boolean = true;
    }

    part def ImplantedReceiverStimulator {
        port rfInput : RadioFrequencyPort;
        port stimulationOutput : StimulationPort;
        port telemetryOutput : RadioFrequencyPort;
        port power : PowerPort;

        attribute hermeticCaseIntegrity : Boolean = true;
        attribute maximumComplianceVoltage : Voltage = 12.0;
        attribute maximumStimCurrent : Current = 900.0;
        attribute operatingMode : ImplantOperatingMode = ImplantOperatingMode::stimulating;

        perform action receiveAndDecode : TransmitAcrossSkin;
        perform action generatePulse : GenerateBiphasicPulse;
    }

    part def ElectrodeArray {
        port stimulationInput : StimulationPort;
        port neuralOutput : NeuralInterfacePort;

        attribute electrodeCount : Integer = 22;
        attribute insertionDepth : Real = 20.0;
        attribute nominalElectrodeImpedance : Impedance = 7500.0;
        attribute contactState : ElectrodeContactState = ElectrodeContactState::inactive;

        perform action neuralStimulation : StimulateAuditoryNerve;
    }

    part def Cochlea {
        port neuralInput : NeuralInterfacePort;

        attribute tonotopicLowFrequency : Frequency = 188.0;
        attribute tonotopicHighFrequency : Frequency = 7938.0;
        attribute targetNeuralPopulation : String = "auditory nerve fibers";
    }

    part def CochlearImplantSystem {
        doc
        /* The cochlear implant system captures external sound, converts it into encoded electrical stimulation patterns, transmits those patterns through the skin to an implanted receiver, and stimulates the cochlear nerve through an electrode array to provide auditory perception. */

        part externalProcessor : ExternalSoundProcessor;
        part microphoneArray : MicrophoneArray;
        part speechProcessor : SpeechProcessor;
        part transmitterCoil : ExternalTransmitterCoil;
        part receiverStimulator : ImplantedReceiverStimulator;
        part electrodeArray : ElectrodeArray;
        part cochlea : Cochlea;

        attribute mode : ImplantOperatingMode;
        attribute maximumSystemLatency : TimeDuration = 0.012;
        attribute acousticInputRangeLow : SoundPressureLevel = 25.0;
        attribute acousticInputRangeHigh : SoundPressureLevel = 100.0;
        attribute stimulationChannelCount : Integer = 22;

        connect microphoneArray.signalOutput to speechProcessor.signalInput;
        connect speechProcessor.audioOutput to transmitterCoil.digitalInput;
        connect transmitterCoil.rfOutput to receiverStimulator.rfInput;
        connect receiverStimulator.stimulationOutput to electrodeArray.stimulationInput;
        connect electrodeArray.neuralOutput to cochlea.neuralInput;

        exhibit state lifecycle : ImplantLifecycle;
    }

    requirement def PrimaryFunctionRequirement {
        doc
        /* The system shall restore functional auditory sensation by transforming acoustic sound into controlled electrical stimulation of the auditory nerve. */

        subject implant : CochlearImplantSystem;

        require constraint {
            implant.stimulationChannelCount >= 12
        }
    }

    requirement def SoundCaptureRequirement {
        doc
        /* The external processor shall capture speech-band acoustic input across normal conversational sound levels. */

        subject implant : CochlearImplantSystem;

        require constraint {
            implant.acousticInputRangeLow <= 30.0 and
            implant.acousticInputRangeHigh >= 90.0
        }
    }

    requirement def LatencyRequirement {
        doc
        /* The system shall maintain low end-to-end latency from sound capture to neural stimulation. */

        subject implant : CochlearImplantSystem;

        require constraint {
            implant.maximumSystemLatency <= 0.015
        }
    }

    requirement def ChargeBalanceRequirement {
        doc
        /* The implanted stimulator shall deliver charge-balanced biphasic pulses to reduce tissue damage and electrode corrosion risk. */

        subject receiver : ImplantedReceiverStimulator;

        require constraint {
            receiver.maximumComplianceVoltage >= 10.0 and
            receiver.maximumStimCurrent <= 1000.0
        }
    }

    requirement def ElectrodeArrayRequirement {
        doc
        /* The electrode array shall provide multiple independent stimulation contacts distributed along the cochlear tonotopic axis. */

        subject array : ElectrodeArray;

        require constraint {
            array.electrodeCount >= 16 and
            array.nominalElectrodeImpedance > 1000.0 and
            array.nominalElectrodeImpedance < 20000.0
        }
    }

    requirement def TelemetryRequirement {
        doc
        /* The implanted electronics shall support telemetry for impedance, battery, and status monitoring. */

        subject receiver : ImplantedReceiverStimulator;

        require constraint {
            receiver.hermeticCaseIntegrity == true
        }
    }

    satisfy PrimaryFunctionRequirement by CochlearImplantSystem;
    satisfy SoundCaptureRequirement by CochlearImplantSystem;
    satisfy LatencyRequirement by CochlearImplantSystem;
    satisfy ChargeBalanceRequirement by ImplantedReceiverStimulator;
    satisfy ElectrodeArrayRequirement by ElectrodeArray;
    satisfy TelemetryRequirement by ImplantedReceiverStimulator;
}

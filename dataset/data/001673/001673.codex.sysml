package NestLabsSmartClimateSystem {

  import ScalarValues::*;
  import ISQ::*;
  import SI::*;

  value def Temperature :> Real {
    unit = "degC";
  }

  value def RelativeHumidity :> Real {
    unit = "%";
  }

  value def Power :> Real {
    unit = "W";
  }

  value def Voltage :> Real {
    unit = "V";
  }

  value def Current :> Real {
    unit = "A";
  }

  value def Duration :> Real {
    unit = "s";
  }

  value def Energy :> Real {
    unit = "kWh";
  }

  value def OccupancyConfidence :> Real {
    unit = "%";
  }

  value def AirQualityIndex :> Integer {
    unit = "AQI";
  }

  enum def HVACMode {
    enum heat;
    enum cool;
    enum auto;
    enum eco;
    enum off;
  }

  enum def FanMode {
    enum auto;
    enum on;
    enum circulate;
  }

  enum def EquipmentCommand {
    enum heatStage1On;
    enum heatStage2On;
    enum coolingOn;
    enum fanOn;
    enum humidifierOn;
    enum dehumidifierOn;
    enum allOff;
  }

  enum def ConnectivityState {
    enum connected;
    enum disconnected;
    enum provisioning;
  }

  item def TemperatureSample {
    attribute measuredTemperature : Temperature;
    attribute sampleAge : Duration;
    attribute sensorHealth : Real;
  }

  item def HumiditySample {
    attribute measuredHumidity : RelativeHumidity;
    attribute sampleAge : Duration;
  }

  item def OccupancySample {
    attribute occupied : Boolean;
    attribute confidence : OccupancyConfidence;
    attribute sampleAge : Duration;
  }

  item def AirQualitySample {
    attribute index : AirQualityIndex;
    attribute volatileOrganicCompoundsPresent : Boolean;
    attribute smokeDetected : Boolean;
  }

  item def UserPreference {
    attribute targetHeatTemperature : Temperature;
    attribute targetCoolTemperature : Temperature;
    attribute selectedMode : HVACMode;
    attribute selectedFanMode : FanMode;
    attribute ecoEnabled : Boolean;
  }

  item def ScheduleProfile {
    attribute weekdayWakeTemperature : Temperature;
    attribute weekdayAwayTemperature : Temperature;
    attribute weekdaySleepTemperature : Temperature;
    attribute weekendWakeTemperature : Temperature;
    attribute weekendAwayTemperature : Temperature;
    attribute weekendSleepTemperature : Temperature;
  }

  item def HVACControlSignal {
    attribute command : EquipmentCommand;
    attribute requestedMode : HVACMode;
    attribute requestedFanMode : FanMode;
    attribute minimumRunTime : Duration;
  }

  item def EnergyReport {
    attribute heatingEnergyUsed : Energy;
    attribute coolingEnergyUsed : Energy;
    attribute fanEnergyUsed : Energy;
    attribute ecoSavingsEstimate : Energy;
  }

  item def CloudMessage {
    attribute messageId : String;
    attribute encrypted : Boolean;
    attribute payloadValid : Boolean;
  }

  port def TemperatureSensorPort {
    out item temperatureSample : TemperatureSample;
  }

  port def HumiditySensorPort {
    out item humiditySample : HumiditySample;
  }

  port def OccupancySensorPort {
    out item occupancySample : OccupancySample;
  }

  port def AirQualitySensorPort {
    out item airQualitySample : AirQualitySample;
  }

  port def UserInterfacePort {
    in item preferenceInput : UserPreference;
    out item displayedTemperature : TemperatureSample;
    out item displayedEnergyReport : EnergyReport;
  }

  port def HVACEquipmentPort {
    out item controlSignal : HVACControlSignal;
    in item equipmentStatus : HVACControlSignal;
  }

  port def CloudServicePort {
    in item outboundMessage : CloudMessage;
    out item inboundPreference : UserPreference;
    out item inboundSchedule : ScheduleProfile;
  }

  port def PowerPort {
    in attribute supplyVoltage : Voltage;
    in attribute supplyCurrent : Current;
    out attribute consumedPower : Power;
  }

  part def NestLearningThermostat {
    attribute currentTemperature : Temperature;
    attribute currentHumidity : RelativeHumidity;
    attribute targetHeatTemperature : Temperature;
    attribute targetCoolTemperature : Temperature;
    attribute activeMode : HVACMode;
    attribute fanMode : FanMode;
    attribute occupied : Boolean;
    attribute learnedScheduleValid : Boolean;
    attribute connectivity : ConnectivityState;
    attribute controlDeadband : Temperature = 0.5;
    attribute minimumCompressorOffTime : Duration = 300.0;
    attribute nominalPowerDraw : Power = 3.0;

    port temperatureIn : TemperatureSensorPort;
    port humidityIn : HumiditySensorPort;
    port occupancyIn : OccupancySensorPort;
    port airQualityIn : AirQualitySensorPort;
    port userInterface : UserInterfacePort;
    port hvacOut : HVACEquipmentPort;
    port cloud : CloudServicePort;
    port power : PowerPort;

    part embeddedController : ClimateControlProcessor;
    part learningEngine : ScheduleLearningEngine;
    part wirelessModule : ConnectivityModule;
    part displayAssembly : UserDisplay;
    part safetySupervisor : EquipmentSafetySupervisor;

    action def SenseIndoorEnvironment {
      in item temperatureSample : TemperatureSample;
      in item humiditySample : HumiditySample;
      in item occupancySample : OccupancySample;
      out attribute sensedTemperature : Temperature;
      out attribute sensedHumidity : RelativeHumidity;
      out attribute sensedOccupied : Boolean;
    }

    action def SelectComfortTarget {
      in item preference : UserPreference;
      in item schedule : ScheduleProfile;
      in attribute occupied : Boolean;
      out attribute heatTarget : Temperature;
      out attribute coolTarget : Temperature;
      out attribute mode : HVACMode;
    }

    action def ComputeHVACCommand {
      in attribute sensedTemperature : Temperature;
      in attribute heatTarget : Temperature;
      in attribute coolTarget : Temperature;
      in attribute selectedMode : HVACMode;
      out item command : HVACControlSignal;
    }

    action def PublishEnergySummary {
      in item command : HVACControlSignal;
      in attribute runtime : Duration;
      out item report : EnergyReport;
    }

    state def ThermostatOperatingState {
      state initial Provisioning;
      state Idle;
      state Heating;
      state Cooling;
      state Eco;
      state EquipmentProtection;
      state OfflineControl;
      state Fault;

      transition first Provisioning
        then Idle
        accept CloudMessage
        if inboundPreference.payloadValid;

      transition Idle
        then Heating
        if activeMode == HVACMode::heat and currentTemperature < targetHeatTemperature - controlDeadband;

      transition Idle
        then Cooling
        if activeMode == HVACMode::cool and currentTemperature > targetCoolTemperature + controlDeadband;

      transition Idle
        then Eco
        if activeMode == HVACMode::eco or occupied == false;

      transition Heating
        then Idle
        if currentTemperature >= targetHeatTemperature;

      transition Cooling
        then Idle
        if currentTemperature <= targetCoolTemperature;

      transition Cooling
        then EquipmentProtection
        if minimumCompressorOffTime > 0.0;

      transition EquipmentProtection
        then Idle
        after minimumCompressorOffTime;

      transition Idle
        then OfflineControl
        if connectivity == ConnectivityState::disconnected;

      transition OfflineControl
        then Idle
        if connectivity == ConnectivityState::connected;

      transition Idle
        then Fault
        if power.supplyVoltage < 18.0;

      transition Heating
        then Fault
        if power.supplyVoltage < 18.0;

      transition Cooling
        then Fault
        if power.supplyVoltage < 18.0;
    }
  }

  part def ClimateControlProcessor {
    attribute processorTemperature : Temperature;
    attribute controlLoopPeriod : Duration = 5.0;
    attribute commandLatency : Duration;
    port sensorTemperature : TemperatureSensorPort;
    port sensorHumidity : HumiditySensorPort;
    port sensorOccupancy : OccupancySensorPort;
    port commandOutput : HVACEquipmentPort;
  }

  part def ScheduleLearningEngine {
    attribute observationWindow : Duration = 1209600.0;
    attribute learnedScheduleConfidence : OccupancyConfidence;
    attribute ecoThresholdAwayDuration : Duration = 1800.0;
    port occupancyInput : OccupancySensorPort;
    port cloudSchedulePort : CloudServicePort;
  }

  part def ConnectivityModule {
    attribute wifiSignalStrength : Real;
    attribute encryptedTransportEnabled : Boolean = true;
    attribute reconnectInterval : Duration = 30.0;
    attribute state : ConnectivityState;
    port cloudPort : CloudServicePort;
  }

  part def UserDisplay {
    attribute displayBrightness : Real;
    attribute touchEnabled : Boolean = true;
    attribute farSightEnabled : Boolean = true;
    port uiPort : UserInterfacePort;
  }

  part def EquipmentSafetySupervisor {
    attribute compressorShortCycleProtection : Boolean = true;
    attribute furnaceOverrunProtection : Boolean = true;
    attribute maxContinuousHeatRunTime : Duration = 14400.0;
    attribute maxContinuousCoolRunTime : Duration = 14400.0;
    port hvacSafetyPort : HVACEquipmentPort;
  }

  part def IndoorTemperatureSensor {
    attribute accuracy : Temperature = 0.2;
    attribute samplePeriod : Duration = 2.0;
    port sampleOut : TemperatureSensorPort;
  }

  part def IndoorHumiditySensor {
    attribute accuracy : RelativeHumidity = 3.0;
    attribute samplePeriod : Duration = 10.0;
    port sampleOut : HumiditySensorPort;
  }

  part def PresenceDetector {
    attribute infraredRangeMeters : Real = 6.0;
    attribute confidenceThreshold : OccupancyConfidence = 75.0;
    port occupancyOut : OccupancySensorPort;
  }

  part def NestProtectAirSafetySensor {
    attribute smokeAlarmIntegrated : Boolean = true;
    attribute carbonMonoxideAlarmIntegrated : Boolean = true;
    port airQualityOut : AirQualitySensorPort;
  }

  part def ResidentialHVACPlant {
    attribute heatCapacity : Power = 10000.0;
    attribute coolingCapacity : Power = 9000.0;
    attribute fanPower : Power = 500.0;
    attribute humidifierPower : Power = 250.0;
    port equipmentControl : HVACEquipmentPort;
    port powerInput : PowerPort;

    part furnace;
    part airConditionerCompressor;
    part blowerFan;
    part humidifier;
  }

  part def NestCloudService {
    attribute remoteAccessAvailable : Boolean = true;
    attribute analyticsRetentionDays : Integer = 395;
    attribute encryptedAtRest : Boolean = true;
    port thermostatCloudPort : CloudServicePort;
  }

  part def MobileApplication {
    attribute authenticatedUser : Boolean;
    attribute geofenceEnabled : Boolean;
    attribute pushNotificationsEnabled : Boolean;
    port cloudAccess : CloudServicePort;
    port userPreferencePort : UserInterfacePort;
  }

  part def HomeElectricalSupply {
    attribute nominalVoltage : Voltage = 24.0;
    attribute maxCurrent : Current = 1.0;
    port thermostatPower : PowerPort;
    port equipmentPower : PowerPort;
  }

  part def NestLabsHomeClimateSystem {
    doc /* Primary function: maintain residential comfort and energy efficiency by sensing indoor conditions and occupancy, learning occupant preferences, commanding HVAC equipment, and enabling local and cloud-based user control. */

    attribute desiredComfortBandLow : Temperature = 19.0;
    attribute desiredComfortBandHigh : Temperature = 24.0;
    attribute dailyEnergyBudget : Energy = 35.0;
    attribute remoteControlEnabled : Boolean = true;

    part thermostat : NestLearningThermostat;
    part temperatureSensor : IndoorTemperatureSensor;
    part humiditySensor : IndoorHumiditySensor;
    part presenceDetector : PresenceDetector;
    part safetySensor : NestProtectAirSafetySensor;
    part hvacPlant : ResidentialHVACPlant;
    part cloudService : NestCloudService;
    part mobileApp : MobileApplication;
    part electricalSupply : HomeElectricalSupply;

    connect temperatureSensor.sampleOut to thermostat.temperatureIn;
    connect humiditySensor.sampleOut to thermostat.humidityIn;
    connect presenceDetector.occupancyOut to thermostat.occupancyIn;
    connect safetySensor.airQualityOut to thermostat.airQualityIn;
    connect thermostat.hvacOut to hvacPlant.equipmentControl;
    connect thermostat.cloud to cloudService.thermostatCloudPort;
    connect mobileApp.cloudAccess to cloudService.thermostatCloudPort;
    connect thermostat.userInterface to mobileApp.userPreferencePort;
    connect electricalSupply.thermostatPower to thermostat.power;
    connect electricalSupply.equipmentPower to hvacPlant.powerInput;
  }

  requirement def MaintainComfort {
    subject system : NestLabsHomeClimateSystem;
    require constraint {
      system.thermostat.currentTemperature >= system.desiredComfortBandLow and
      system.thermostat.currentTemperature <= system.desiredComfortBandHigh
    }
  }

  requirement def ReduceEnergyUseWhenAway {
    subject system : NestLabsHomeClimateSystem;
    require constraint {
      system.thermostat.occupied == false implies
      system.thermostat.activeMode == HVACMode::eco
    }
  }

  requirement def ProtectHVACEquipment {
    subject thermostat : NestLearningThermostat;
    require constraint {
      thermostat.minimumCompressorOffTime >= 300.0
    }
  }

  requirement def EnableRemoteControl {
    subject system : NestLabsHomeClimateSystem;
    require constraint {
      system.remoteControlEnabled implies
      system.thermostat.connectivity == ConnectivityState::connected
    }
  }

  requirement def UseEncryptedCloudCommunication {
    subject module : ConnectivityModule;
    require constraint {
      module.encryptedTransportEnabled == true
    }
  }

  requirement def ProvideEnergyFeedback {
    subject system : NestLabsHomeClimateSystem;
    require constraint {
      system.dailyEnergyBudget > 0.0
    }
  }

  satisfy MaintainComfort by NestLabsHomeClimateSystem::thermostat;
  satisfy ReduceEnergyUseWhenAway by NestLabsHomeClimateSystem::thermostat;
  satisfy ProtectHVACEquipment by NestLearningThermostat::safetySupervisor;
  satisfy EnableRemoteControl by NestLabsHomeClimateSystem::cloudService;
  satisfy UseEncryptedCloudCommunication by ConnectivityModule;
  satisfy ProvideEnergyFeedback by NestLearningThermostat::PublishEnergySummary;
}

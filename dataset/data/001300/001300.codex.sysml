package UltraWidebandTrackingSystem {

    import ScalarValues::*;
    import SI::*;

    attribute def Distance_m :> Real;
    attribute def Time_ns :> Real;
    attribute def Frequency_Hz :> Real;
    attribute def Power_dBm :> Real;
    attribute def DataRate_bps :> Real;
    attribute def Probability :> Real;
    attribute def Count :> Integer;

    item def UWBFrame {
        attribute preambleLength : Count;
        attribute channelNumber : Count;
        attribute centerFrequency : Frequency_Hz;
        attribute transmitPower : Power_dBm;
        attribute payloadRate : DataRate_bps;
    }

    item def RangingPoll :> UWBFrame {
        attribute sequenceNumber : Count;
    }

    item def RangingResponse :> UWBFrame {
        attribute pollReceiveTime : Time_ns;
        attribute responseTransmitTime : Time_ns;
    }

    item def RangingFinal :> UWBFrame {
        attribute pollTransmitTime : Time_ns;
        attribute responseReceiveTime : Time_ns;
        attribute finalTransmitTime : Time_ns;
    }

    item def TimeOfFlightMeasurement {
        attribute roundTripTime : Time_ns;
        attribute replyDelay : Time_ns;
        attribute timeOfFlight : Time_ns;
        attribute estimatedRange : Distance_m;
        attribute confidence : Probability;
    }

    item def PositionEstimate {
        attribute x : Distance_m;
        attribute y : Distance_m;
        attribute z : Distance_m;
        attribute uncertaintyRadius : Distance_m;
        attribute confidence : Probability;
    }

    item def SynchronizationPulse {
        attribute epochTime : Time_ns;
        attribute driftCorrection : Time_ns;
    }

    item def LocationReport {
        attribute tagId : Count;
        attribute position : PositionEstimate;
        attribute updateTime : Time_ns;
    }

    port def UWBTransceiverPort {
        out item txFrame : UWBFrame;
        in item rxFrame : UWBFrame;
    }

    port def TimeSyncPort {
        out item syncOut : SynchronizationPulse;
        in item syncIn : SynchronizationPulse;
    }

    port def MeasurementPort {
        out item measurement : TimeOfFlightMeasurement;
    }

    port def PositionPort {
        out item position : PositionEstimate;
    }

    port def ReportPort {
        out item report : LocationReport;
    }

    port def PowerPort {
        in attribute supplyVoltage : Real;
        in attribute supplyCurrent : Real;
    }

    part def UWBRadio {
        attribute channelNumber : Count = 9;
        attribute centerFrequency : Frequency_Hz = 7987200000.0;
        attribute bandwidth : Frequency_Hz = 499200000.0;
        attribute transmitPower : Power_dBm = -14.3;
        attribute receiverSensitivity : Power_dBm = -93.0;
        attribute maximumPayloadRate : DataRate_bps = 6800000.0;

        port antenna : UWBTransceiverPort;
        port power : PowerPort;

        action transmitFrame {
            in item frame : UWBFrame;
            out item emittedFrame : UWBFrame;
        }

        action receiveFrame {
            in item receivedFrame : UWBFrame;
            out item decodedFrame : UWBFrame;
        }
    }

    part def PrecisionClock {
        attribute nominalFrequency : Frequency_Hz = 38400000.0;
        attribute timestampResolution : Time_ns = 1.0;
        attribute maximumDriftPerSecond : Time_ns = 20.0;

        port sync : TimeSyncPort;

        action timestampEvent {
            out attribute timestamp : Time_ns;
        }

        action applyDriftCorrection {
            in item correction : SynchronizationPulse;
        }
    }

    part def UWBTag {
        attribute tagId : Count;
        attribute nominalUpdateRate : Frequency_Hz = 10.0;
        attribute maximumRange : Distance_m = 80.0;

        part radio : UWBRadio;
        part clock : PrecisionClock;

        port uwb : UWBTransceiverPort = radio.antenna;
        port sync : TimeSyncPort = clock.sync;

        action initiateRanging {
            out item poll : RangingPoll;
        }

        action completeRangingExchange {
            in item response : RangingResponse;
            out item final : RangingFinal;
        }

        state def TagOperatingState {
            state idle;
            state preparingPoll;
            state transmittingPoll;
            state awaitingResponse;
            state transmittingFinal;
            state sleeping;

            entry action initializeRadio;
            transition first idle;
            transition idle_to_preparing
                first idle
                then preparingPoll
                accept after 100.0 ms;
            transition preparing_to_transmitting
                first preparingPoll
                then transmittingPoll;
            transition transmitting_to_awaiting
                first transmittingPoll
                then awaitingResponse;
            transition response_received
                first awaitingResponse
                then transmittingFinal
                accept item RangingResponse;
            transition final_sent
                first transmittingFinal
                then sleeping;
            transition wake
                first sleeping
                then idle
                accept after 100.0 ms;
        }
    }

    part def UWBAnchor {
        attribute anchorId : Count;
        attribute fixedX : Distance_m;
        attribute fixedY : Distance_m;
        attribute fixedZ : Distance_m;

        part radio : UWBRadio;
        part clock : PrecisionClock;

        port uwb : UWBTransceiverPort = radio.antenna;
        port sync : TimeSyncPort = clock.sync;
        port measurementOut : MeasurementPort;

        action respondToPoll {
            in item poll : RangingPoll;
            out item response : RangingResponse;
        }

        action calculateTimeOfFlight {
            in item final : RangingFinal;
            out item measurement : TimeOfFlightMeasurement;
        }

        state def AnchorRangingState {
            state listening;
            state timestampingPoll;
            state sendingResponse;
            state awaitingFinal;
            state computingRange;
            state publishingMeasurement;

            transition first listening;
            transition poll_detected
                first listening
                then timestampingPoll
                accept item RangingPoll;
            transition timestamp_done
                first timestampingPoll
                then sendingResponse;
            transition response_done
                first sendingResponse
                then awaitingFinal;
            transition final_detected
                first awaitingFinal
                then computingRange
                accept item RangingFinal;
            transition range_done
                first computingRange
                then publishingMeasurement;
            transition published
                first publishingMeasurement
                then listening;
        }
    }

    part def AnchorArray {
        part anchorA : UWBAnchor {
            attribute anchorId = 1;
            attribute fixedX = 0.0;
            attribute fixedY = 0.0;
            attribute fixedZ = 3.0;
        }

        part anchorB : UWBAnchor {
            attribute anchorId = 2;
            attribute fixedX = 20.0;
            attribute fixedY = 0.0;
            attribute fixedZ = 3.0;
        }

        part anchorC : UWBAnchor {
            attribute anchorId = 3;
            attribute fixedX = 20.0;
            attribute fixedY = 15.0;
            attribute fixedZ = 3.0;
        }

        part anchorD : UWBAnchor {
            attribute anchorId = 4;
            attribute fixedX = 0.0;
            attribute fixedY = 15.0;
            attribute fixedZ = 3.0;
        }

        port measurementA : MeasurementPort = anchorA.measurementOut;
        port measurementB : MeasurementPort = anchorB.measurementOut;
        port measurementC : MeasurementPort = anchorC.measurementOut;
        port measurementD : MeasurementPort = anchorD.measurementOut;
    }

    part def LocationEngine {
        attribute minimumAnchorsRequired : Count = 3;
        attribute maximumAcceptedRangeError : Distance_m = 0.30;
        attribute outputUpdateRate : Frequency_Hz = 10.0;

        port positionOut : PositionPort;

        action collectMeasurements {
            in item m1 : TimeOfFlightMeasurement;
            in item m2 : TimeOfFlightMeasurement;
            in item m3 : TimeOfFlightMeasurement;
            in item m4 : TimeOfFlightMeasurement;
        }

        action estimatePosition {
            in item m1 : TimeOfFlightMeasurement;
            in item m2 : TimeOfFlightMeasurement;
            in item m3 : TimeOfFlightMeasurement;
            in item m4 : TimeOfFlightMeasurement;
            out item position : PositionEstimate;
        }

        action rejectOutlierMeasurements {
            in item rawPosition : PositionEstimate;
            out item filteredPosition : PositionEstimate;
        }

        state def LocationEngineState {
            state waitingForMeasurements;
            state validatingMeasurements;
            state solvingMultilateration;
            state filteringEstimate;
            state publishingPosition;

            transition first waitingForMeasurements;
            transition enough_measurements
                first waitingForMeasurements
                then validatingMeasurements;
            transition valid
                first validatingMeasurements
                then solvingMultilateration;
            transition solved
                first solvingMultilateration
                then filteringEstimate;
            transition filtered
                first filteringEstimate
                then publishingPosition;
            transition published
                first publishingPosition
                then waitingForMeasurements;
            transition invalid
                first validatingMeasurements
                then waitingForMeasurements;
        }
    }

    part def ApplicationGateway {
        attribute reportRate : Frequency_Hz = 10.0;
        attribute retainedHistorySeconds : Real = 3600.0;

        port positionIn : PositionPort;
        port reportOut : ReportPort;

        action createLocationReport {
            in item position : PositionEstimate;
            out item report : LocationReport;
        }

        action publishReport {
            in item report : LocationReport;
        }
    }

    part def UWBLocationSystem {
        attribute primaryFunction : String =
            "Determine the real-time three-dimensional position of a mobile tag by exchanging ultra-wideband ranging messages with fixed anchors, converting time-of-flight measurements into distances, and solving a multilateration estimate for downstream applications.";

        part mobileTag : UWBTag {
            attribute tagId = 1001;
        }

        part anchors : AnchorArray;
        part locationEngine : LocationEngine;
        part gateway : ApplicationGateway;

        port report : ReportPort = gateway.reportOut;

        connection tag_to_anchorA connect mobileTag.uwb to anchors.anchorA.uwb;
        connection tag_to_anchorB connect mobileTag.uwb to anchors.anchorB.uwb;
        connection tag_to_anchorC connect mobileTag.uwb to anchors.anchorC.uwb;
        connection tag_to_anchorD connect mobileTag.uwb to anchors.anchorD.uwb;

        connection anchorA_measurement connect anchors.measurementA to locationEngine;
        connection anchorB_measurement connect anchors.measurementB to locationEngine;
        connection anchorC_measurement connect anchors.measurementC to locationEngine;
        connection anchorD_measurement connect anchors.measurementD to locationEngine;

        connection position_to_gateway connect locationEngine.positionOut to gateway.positionIn;
    }

    requirement def PrimaryFunctionRequirement {
        subject system : UWBLocationSystem;

        require constraint {
            system.primaryFunction ==
            "Determine the real-time three-dimensional position of a mobile tag by exchanging ultra-wideband ranging messages with fixed anchors, converting time-of-flight measurements into distances, and solving a multilateration estimate for downstream applications."
        }
    }

    requirement def RangingAccuracyRequirement {
        subject engine : LocationEngine;

        attribute requiredAccuracy : Distance_m = 0.30;

        require constraint {
            engine.maximumAcceptedRangeError <= requiredAccuracy
        }
    }

    requirement def AnchorAvailabilityRequirement {
        subject engine : LocationEngine;

        require constraint {
            engine.minimumAnchorsRequired >= 3
        }
    }

    requirement def UpdateRateRequirement {
        subject system : UWBLocationSystem;

        attribute minimumUpdateRate : Frequency_Hz = 5.0;

        require constraint {
            system.locationEngine.outputUpdateRate >= minimumUpdateRate
        }
    }

    requirement def RadioBandwidthRequirement {
        subject radio : UWBRadio;

        attribute minimumBandwidth : Frequency_Hz = 499000000.0;

        require constraint {
            radio.bandwidth >= minimumBandwidth
        }
    }

    requirement def OperatingRangeRequirement {
        subject tag : UWBTag;

        attribute minimumOperationalRange : Distance_m = 50.0;

        require constraint {
            tag.maximumRange >= minimumOperationalRange
        }
    }

    part uwbTrackingDeployment : UWBLocationSystem;

    satisfy PrimaryFunctionRequirement by uwbTrackingDeployment;
    satisfy UpdateRateRequirement by uwbTrackingDeployment;
    satisfy AnchorAvailabilityRequirement by uwbTrackingDeployment.locationEngine;
    satisfy OperatingRangeRequirement by uwbTrackingDeployment.mobileTag;
}

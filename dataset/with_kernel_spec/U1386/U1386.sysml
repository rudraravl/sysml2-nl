package BiomimeticAdhesionSystem {
	doc
	/*
	 * Biomimetic adhesion system modeling a gecko-inspired robotic gripper.
	 * Adhesion is generated by van der Waals forces through a hierarchical
	 * structure of pads, toes, lamellae, and microscopic setae.
	 * Attachment uses normal + shear loading; detachment uses controlled peeling.
	 * Includes overload protection and a parallel operational/safety state machine.
	 */

	private import ScalarValues::*;

	// ---- Value types ----

	attribute def ForceValue :> Real;
	attribute def AngleValue :> Real;
	attribute def AreaValue :> Real;
	attribute def LengthValue :> Real;
	attribute def PressureValue :> Real;

	// ---- Enumerations ----

	enum def GripperStatus {
		detached;
		approaching;
		engaging;
		adhered;
		releasing;
		emergencyRelease;
	}

	// ---- Signal items ----

	item def StartApproach;
	item def SurfaceContact;
	item def AdhesionEngaged;
	item def ReleaseCommand;
	item def ReleaseComplete;
	item def Overload;

	// ---- Ports ----

	port def ControlPort {
		in startAttach : Boolean;
		in startDetach : Boolean;
		out status : GripperStatus;
	}

	port def MechanicalInterfacePort {
		out normalForce : ForceValue;
		out shearForce : ForceValue;
		in contactLoad : ForceValue;
	}

	port def ControlSignalPort {
		out peelAngleCmd : AngleValue;
	}

	port def LoadReportPort {
		out load : ForceValue;
		out overload : Boolean;
	}

	// ---- Core hierarchical parts ----

	part def Seta {
		attribute length : LengthValue;
		attribute diameter : LengthValue;
		attribute adhesionForce : ForceValue;
	}

	part def Lamella {
		part setae : Seta[1000000..5000000];
		attribute flexibility : Real;
		attribute thickness : LengthValue;
	}

	part def Toe {
		part lamellae : Lamella[5..20];
		attribute peelAngle : AngleValue;
		attribute engaged : Boolean;
	}

	part def AdhesivePad {
		port surfaceInterface : MechanicalInterfacePort;
		port controlIn : ControlSignalPort;
		port loadReport : LoadReportPort;
		part toes : Toe[3..8];
		attribute padArea : AreaValue;
		attribute maxPadLoad : ForceValue;
	}

	part def AngleController {
		port controlOut : ControlSignalPort;
		attribute targetPeelAngle : AngleValue;
		attribute maxPeelAngle : AngleValue;
	}

	part def LoadSensor {
		port loadIn : LoadReportPort;
		attribute measuredLoad : ForceValue;
		attribute maxLoad : ForceValue;
		attribute overloadDetected : Boolean;
	}

	part def Surface {
		attribute roughness : Real;
		attribute isFlat : Boolean;
		attribute contactArea : AreaValue;
	}

	// ---- Actions ----

	action def AttachAction {
		in targetSurface : Surface;
		out normalForce : ForceValue;
		out shearForce : ForceValue;
	}

	action def DetachAction {
		in peelAngle : AngleValue;
	}

	action def EmergencyReleaseAction {
		out rapidPeelAngle : AngleValue;
	}

	// ---- State machine ----

	state def GripperStates parallel {
		state operationalStates {
			entry; then detached;
			state detached;
			accept StartApproach then approaching;
			state approaching;
			accept SurfaceContact then engaging;
			state engaging {
				entry action attach : AttachAction;
			}
			accept AdhesionEngaged then adhered;
			state adhered;
			accept ReleaseCommand then releasing;
			state releasing {
				entry action detach : DetachAction;
			}
			accept ReleaseComplete then detached;
		}
		state safetyStates {
			entry; then normal;
			state normal;
			accept Overload then emergencyRelease;
			state emergencyRelease {
				entry action emergencyRelease : EmergencyReleaseAction;
			}
			accept ReleaseComplete then normal;
		}
	}

	// ---- Gripper definition ----

	part def GeckoGripper {
		port controlPort : ControlPort;
		attribute maxLoad : ForceValue;
		attribute currentLoad : ForceValue;
		attribute currentStatus : GripperStatus;

		part pads : AdhesivePad[1..*];
		part angleController : AngleController;
		part loadSensor : LoadSensor;

		state gripperStates : GripperStates;

		assert constraint loadWithinCapacity {
			currentLoad <= maxLoad
		}
	}

	// ---- Assembled usage ----

	part gripper : GeckoGripper {
		:>> maxLoad = 50;
		:>> currentLoad = 0;
		:>> currentStatus = GripperStatus::detached;

		part redefines pads[4] {
			:>> padArea = 0.01;
			:>> maxPadLoad = 15;
			part redefines toes[6] {
				:>> peelAngle = 0;
				part redefines lamellae[10] {
					:>> flexibility = 0.8;
					:>> thickness = 0.001;
					part redefines setae[2000000] {
						:>> length = 100e-6;
						:>> diameter = 0.2e-6;
						:>> adhesionForce = 200e-6;
					}
				}
			}
		}

		part redefines angleController {
			:>> targetPeelAngle = 30;
			:>> maxPeelAngle = 90;
		}

		part redefines loadSensor {
			:>> maxLoad = 50;
			:>> measuredLoad = 0;
			:>> overloadDetected = false;
		}

		connect angleController.controlOut to pads.controlIn;
		connect pads.loadReport to loadSensor.loadIn;
	}

	// ---- Requirements ----

	requirement def AdhesionCapacityRequirement {
		subject gripper : GeckoGripper;
		attribute minLoadCapacity : ForceValue;
		assert constraint {
			gripper.maxLoad >= minLoadCapacity
		}
	}

	requirement def ControllableReleaseRequirement {
		subject gripper : GeckoGripper;
		attribute maxPeelAngle : AngleValue;
		assert constraint {
			gripper.angleController.targetPeelAngle <= maxPeelAngle
		}
	}

	requirement def OverloadProtectionRequirement {
		subject gripper : GeckoGripper;
		attribute maxLoad : ForceValue;
		assert constraint {
			gripper.loadSensor.measuredLoad > maxLoad implies
			gripper.loadSensor.overloadDetected == true
		}
	}

	requirement def HierarchicalConformabilityRequirement {
		subject pad : AdhesivePad;
		assert constraint {
			pad.toes.lamellae.flexibility > 0.0 and
			pad.toes.lamellae.setae.length > 0.0
		}
	}

	requirement def VanDerWaalsAdhesionRequirement {
		subject pad : AdhesivePad;
		assert constraint {
			pad.toes.lamellae.setae.adhesionForce > 0.0
		}
	}

	// ---- Requirement usages ----

	requirement adhesionCapacity : AdhesionCapacityRequirement {
		subject = gripper;
		:>> minLoadCapacity = 40;
	}

	requirement controllableRelease : ControllableReleaseRequirement {
		subject = gripper;
		:>> maxPeelAngle = 90;
	}

	requirement overloadProtection : OverloadProtectionRequirement {
		subject = gripper;
		:>> maxLoad = 50;
	}

	requirement conformability : HierarchicalConformabilityRequirement {
		subject = gripper.pads;
	}

	requirement vanDerWaalsAdhesion : VanDerWaalsAdhesionRequirement {
		subject = gripper.pads;
	}
}

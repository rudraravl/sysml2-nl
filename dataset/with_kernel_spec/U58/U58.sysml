package 'Gravity-Fed IV Infusion System' {
    private import ScalarValues::*;
    
    attribute def Volume :> Real;
    attribute def DropRate :> Real;
    attribute def FlowRate :> Real;
    attribute def Height :> Real;
    
    item def IVFluid;
    item def Air;
    
    port def FluidOutPort {
        out item fluid : IVFluid;
    }
    port def FluidInPort {
        in item fluid : IVFluid;
    }
    port def AirVentPort {
        in item air : Air;
    }
    
    part def IVBag {
        port fluidOut : FluidOutPort;
        attribute volume : Volume;
        attribute suspensionHeight : Height;
    }
    
    part def DripChamber {
        port fluidIn : FluidInPort;
        port fluidOut : FluidOutPort;
        port airVent : AirVentPort;
        attribute dropRate : DropRate;
        attribute fillLevel : Volume;
    }
    
    part def RollerClamp {
        attribute constrictionLevel : Real;
    }
    
    part def DeliveryTubing {
        port fluidIn : FluidInPort;
        port fluidOut : FluidOutPort;
        part rollerClamp : RollerClamp;
    }
    
    part def PatientConnection {
        port fluidIn : FluidInPort;
    }
    
    action def PrimeCompleteSignal;
    action def StartSignal;
    action def PauseSignal;
    action def ResumeSignal;
    action def StopSignal;
    action def ResetSignal;
    action def EmptyDetectedSignal;
    action def OverfilledDetectedSignal;
    action def AlarmClearedSignal;
    
    state def IVSystemBehavior {
        entry; then priming;
        state priming;
        transition priming_to_ready
            first priming
            accept PrimeCompleteSignal
            then ready;
        state ready;
        transition ready_to_running
            first ready
            accept StartSignal
            then running;
        state running;
        transition running_to_paused
            first running
            accept PauseSignal
            then paused;
        transition running_to_stopped
            first running
            accept StopSignal
            then stopped;
        transition running_to_alarmEmpty
            first running
            accept EmptyDetectedSignal
            then alarmEmpty;
        transition running_to_alarmOverfilled
            first running
            accept OverfilledDetectedSignal
            then alarmOverfilled;
        state paused;
        transition paused_to_running
            first paused
            accept ResumeSignal
            then running;
        transition paused_to_stopped
            first paused
            accept StopSignal
            then stopped;
        state stopped;
        transition stopped_to_ready
            first stopped
            accept ResetSignal
            then ready;
        state alarmEmpty;
        state alarmOverfilled;
        transition alarmEmpty_to_ready
            first alarmEmpty
            accept AlarmClearedSignal
            then ready;
        transition alarmOverfilled_to_ready
            first alarmOverfilled
            accept AlarmClearedSignal
            then ready;
    }
    
    part def IVInfusionSystem {
        part ivBag : IVBag;
        part dripChamber : DripChamber;
        part deliveryTubing : DeliveryTubing;
        part patientConn : PatientConnection;
        
        state systemBehavior : IVSystemBehavior;
        
        flow of IVFluid from ivBag.fluidOut.fluid to dripChamber.fluidIn.fluid;
        flow of IVFluid from dripChamber.fluidOut.fluid to deliveryTubing.fluidIn.fluid;
        flow of IVFluid from deliveryTubing.fluidOut.fluid to patientConn.fluidIn.fluid;
    }
    
    part ivSystem : IVInfusionSystem;
    
    requirement def ControlledDeliveryReq {
        doc /* The gravity-fed IV infusion system shall deliver sterile fluid to a patient at a controlled rate. */
    }
    requirement def PrimingReq {
        doc /* The system shall include a priming phase to fill the drip chamber and purge air from the tubing. */
    }
    requirement def MonitoringReq {
        doc /* The system shall monitor drip chamber fill level and generate alarms for empty or overfilled conditions. */
    }
    requirement def FlowControlReq {
        doc /* The roller clamp shall allow manual adjustment of the fluid flow rate. */
    }
    requirement def GravityFeedReq {
        doc /* The system shall operate using hydrostatic pressure generated by the suspended IV bag height. */
    }
}

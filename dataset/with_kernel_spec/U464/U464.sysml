package 'Airlift Pumping System' {
	private import ISQ::*;
	private import ScalarValues::*;
	public import Definitions::*;

	package Definitions {
		item def CompressedAir {
			attribute pressure : PressureValue;
			attribute temperature : ThermodynamicTemperatureValue;
		}
		item def Fluid {
			attribute density : DensityValue;
			attribute viscosity : DynamicViscosityValue;
		}
		item def AirFluidMixture {
			attribute voidFraction : Real;
			attribute mixtureDensity : DensityValue;
		}
		item def StartCommand;
		item def StopCommand;
		item def FaultCondition;
		item def ResetCommand;

		port def AirOutPort {
			out item air : CompressedAir;
		}
		port def FluidOutPort {
			out item fluid : Fluid;
		}
		port def MixtureOutPort {
			out item mixture : AirFluidMixture;
		}

		action def GenerateCompressedAir {
			out outAir : CompressedAir;
		}
		action def RegulatePressure {
			in inAir : CompressedAir;
			in targetPressure : PressureValue;
			out outAir : CompressedAir;
		}
		action def InjectAir {
			in inAir : CompressedAir;
			in inFluid : Fluid;
			out outMixture : AirFluidMixture;
		}
		action def SeparateMixture {
			in inMixture : AirFluidMixture;
			out outFluid : Fluid;
			out outAir : CompressedAir;
		}
		action def MeasureFlow {
			in inFluid : Fluid;
			out outFluid : Fluid;
			out flowRate : VolumeFlowRateValue;
		}
		action def BuildPressure {
			in targetPressure : PressureValue;
			out achievedPressure : PressureValue;
		}
		action def ShutdownProcess;
		action def HandleFault;
		action def PumpCycle;

		part def AirCompressor {
			port airOut : AirOutPort;
			attribute dischargePressure : PressureValue;
		}
		part def PressureRegulator {
			port airIn : ~AirOutPort;
			port airOut : AirOutPort;
			attribute setPressure : PressureValue;
		}
		part def SourceReservoir {
			port fluidOut : FluidOutPort;
			item fluid : Fluid;
			attribute volume : VolumeValue;
			attribute level : LengthValue;
		}
		part def RiserPipe {
			port airIn : ~AirOutPort;
			port fluidIn : ~FluidOutPort;
			port mixtureOut : MixtureOutPort;
			attribute length : LengthValue;
			attribute diameter : LengthValue;
			attribute submersionDepth : LengthValue;
		}
		part def AirliftPump {
			port airIn : ~AirOutPort;
			port fluidIn : ~FluidOutPort;
			port mixtureOut : MixtureOutPort;
			part riser : RiserPipe;
			flow of air : CompressedAir from airIn.air to riser.airIn.air;
			flow of fluid : Fluid from fluidIn.fluid to riser.fluidIn.fluid;
			flow of mixture : AirFluidMixture from riser.mixtureOut.mixture to mixtureOut.mixture;
		}
		part def AirFluidSeparator {
			port mixtureIn : ~MixtureOutPort;
			port airVent : AirOutPort;
			port fluidOut : FluidOutPort;
		}
		part def FlowMeter {
			port fluidIn : ~FluidOutPort;
			port fluidOut : FluidOutPort;
			attribute measuredFlowRate : VolumeFlowRateValue;
		}
		part def DestinationTank {
			port fluidIn : ~FluidOutPort;
			item fluid : Fluid;
			attribute capacity : VolumeValue;
			attribute currentLevel : Real;
		}
		part def Atmosphere {
			port airIn : ~AirOutPort;
		}

		state def SystemStates {
			in regulator : PressureRegulator;
			in compressor : AirCompressor;
			in pump : AirliftPump;
			in separator : AirFluidSeparator;
			in flowMeter : FlowMeter;
			in destTank : DestinationTank;
			in sourceReservoir : SourceReservoir;

			state idle;
			state starting {
				do action buildPressure : BuildPressure {
					in targetPressure = regulator.setPressure;
					out achievedPressure;
				}
			}
			state operating {
				do action pumpCycle : PumpCycle;
			}
			state shuttingDown {
				do action shutdown : ShutdownProcess;
			}
			state fault {
				do action handleFault : HandleFault;
			}

			transition idle to starting
				on accept startCmd : StartCommand;
			transition starting to operating
				if buildPressure.achievedPressure >= regulator.setPressure;
			transition operating to shuttingDown
				on accept stopCmd : StopCommand;
			transition operating to fault
				on accept faultEv : FaultCondition;
			transition shuttingDown to idle;
			transition fault to idle
				on accept resetEv : ResetCommand;
		}

		requirement def AirliftSystemReq {
			text "The airlift pumping system shall transfer fluid from a lower source reservoir to a higher destination tank using buoyancy generated by injected compressed air.";
		}
		requirement def PressureControlReq {
			text "The pressure regulator shall maintain air pressure at the set level during operation.";
		}
		requirement def SeparationReq {
			text "The air-fluid separator shall separate air from the lifted mixture and vent the air to atmosphere.";
		}
		requirement def FlowMeasurementReq {
			text "The flow meter shall measure the flow rate of the discharged fluid.";
		}
		requirement def LifecycleReq {
			text "The system shall operate through idle, starting, operating, shutting down, and fault states.";
		}
	}

	package Usages {
		requirement airliftReq : AirliftSystemReq;
		requirement pressureReq : PressureControlReq;
		requirement separationReq : SeparationReq;
		requirement flowMeasurementReq : FlowMeasurementReq;
		requirement lifecycleReq : LifecycleReq;

		part context {
			part sourceReservoir : SourceReservoir {
				attribute volume = 10.0 [m^3];
				attribute level = 8.0 [m];
				item fluid : Fluid;
			}
			part compressor : AirCompressor {
				attribute dischargePressure = 600000.0 [Pa];
				perform action generate : GenerateCompressedAir {
					out outAir = airOut.air;
				}
			}
			part pressureRegulator : PressureRegulator {
				attribute setPressure = 500000.0 [Pa];
				perform action regulate : RegulatePressure {
					in inAir = airIn.air;
					in targetPressure = setPressure;
					out outAir = airOut.air;
				}
			}
			part pump : AirliftPump {
				part riser : RiserPipe {
					attribute length = 10.0 [m];
					attribute diameter = 0.1 [m];
					attribute submersionDepth = 8.0 [m];
					perform action inject : InjectAir {
						in inAir = airIn.air;
						in inFluid = fluidIn.fluid;
						out outMixture = mixtureOut.mixture;
					}
				}
			}
			part separator : AirFluidSeparator {
				perform action separate : SeparateMixture {
					in inMixture = mixtureIn.mixture;
					out outFluid = fluidOut.fluid;
					out outAir = airVent.air;
				}
			}
			part flowMeter : FlowMeter {
				perform action measure : MeasureFlow {
					in inFluid = fluidIn.fluid;
					out outFluid = fluidOut.fluid;
					out flowRate = measuredFlowRate;
				}
			}
			part destTank : DestinationTank {
				attribute capacity = 5.0 [m^3];
				attribute currentLevel = 0.0;
				item fluid : Fluid;
			}
			part atmosphere : Atmosphere;

			flow of fluid : Fluid
				from sourceReservoir.fluidOut.fluid to pump.fluidIn.fluid;
			flow of air : CompressedAir
				from compressor.airOut.air to pressureRegulator.airIn.air;
			flow of air : CompressedAir
				from pressureRegulator.airOut.air to pump.airIn.air;
			flow of mixture : AirFluidMixture
				from pump.mixtureOut.mixture to separator.mixtureIn.mixture;
			flow of air : CompressedAir
				from separator.airVent.air to atmosphere.airIn.air;
			flow of fluid : Fluid
				from separator.fluidOut.fluid to flowMeter.fluidIn.fluid;
			flow of fluid : Fluid
				from flowMeter.fluidOut.fluid to destTank.fluidIn.fluid;

			exhibit systemStates : SystemStates {
				in regulator = pressureRegulator;
				in compressor = compressor;
				in pump = pump;
				in separator = separator;
				in flowMeter = flowMeter;
				in destTank = destTank;
				in sourceReservoir = sourceReservoir;
			}
		}
	}
}

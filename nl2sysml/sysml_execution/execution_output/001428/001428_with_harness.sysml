package 'Figure AI Humanoid Robot System' {
	private import ScalarValues::*;
	private import ISQ::*;
	private import SI::*;
	
	attribute def VisionData;
	attribute def AudioData;
	attribute def TactileData;
	attribute def MotorCommand;
	attribute def TaskInstruction;
	attribute def EnvironmentModel;
	attribute def TrajectoryPlan;
	attribute def SafetyStatus {
		attribute isSafe : Boolean;
	}
	attribute def ObjectIdentifier;
	
	value def JointAngle :> ISQ::AngleValue {
		attribute minAngle : ISQ::AngleValue;
		attribute maxAngle : ISQ::AngleValue;
		attribute currentAngle : ISQ::AngleValue;
	}
	
	value def JointTorque :> ISQ::TorqueValue {
		attribute maxTorque : ISQ::TorqueValue;
		attribute currentTorque : ISQ::TorqueValue;
	}
	
	value def GripForce :> ISQ::ForceValue {
		attribute targetForce : ISQ::ForceValue;
		attribute measuredForce : ISQ::ForceValue;
	}
	
	item def SensorData {
		attribute vision : VisionData;
		attribute audio : AudioData;
		attribute tactile : TactileData;
		attribute timestamp : ISQ::TimeValue;
	}
	
	item def MotionPlan {
		attribute trajectory : TrajectoryPlan;
		attribute duration : ISQ::TimeValue;
		attribute priority : Real;
		attribute requiresManipulation : Boolean;
		attribute requiresNavigation : Boolean;
		attribute isIdle : Boolean;
	}
	
	port def SensorPort {
		out visionData : VisionData;
		out audioData : AudioData;
		out tactileData : TactileData;
	}
	
	port def ActuatorPort {
		in motorCmd : MotorCommand;
		out jointAngle : JointAngle;
		out jointTorque : JointTorque;
	}
	
	port def CommunicationPort {
		in taskInstruction : TaskInstruction;
		out safetyStatus : SafetyStatus;
	}
	
	port def PerceptionOutputPort {
		out environmentModel : EnvironmentModel;
	}
	
	port def CognitionInputPort {
		in environmentModel : EnvironmentModel;
		in taskInstruction : TaskInstruction;
	}
	
	port def CognitionOutputPort {
		out trajectoryPlan : TrajectoryPlan;
		out safetyStatus : SafetyStatus;
	}
	
	port def ControlInputPort {
		in trajectoryPlan : TrajectoryPlan;
		in jointFeedback : JointAngle;
	}
	
	part def PerceptionSystem {
		port sensorInput : SensorPort;
		port perceptionOutput : PerceptionOutputPort;
		
		part visionProcessor {
			attribute processingRate : ISQ::FrequencyValue = 30[Hz];
			attribute resolution : Integer = 1920;
		}
		
		part audioProcessor {
			attribute sampleRate : ISQ::FrequencyValue = 16000[Hz];
			attribute channels : Integer = 2;
		}
		
		part tactileProcessor {
			attribute sensitivity : ISQ::ForceValue = 0.1[N];
			attribute responseTime : ISQ::TimeValue = 0.01[s];
		}
		
		part fusionModule {
			attribute updateRate : ISQ::FrequencyValue = 100[Hz];
		}
	}
	
	part def CognitionSystem {
		port cognitionInput : CognitionInputPort;
		port cognitionOutput : CognitionOutputPort;
		
		part taskPlanner {
			attribute planningHorizon : ISQ::TimeValue = 5.0[s];
			attribute replanRate : ISQ::FrequencyValue = 10[Hz];
		}
		
		part safetyMonitor {
			attribute checkInterval : ISQ::TimeValue = 0.01[s];
			attribute safetyMargin : ISQ::LengthValue = 0.1[m];
		}
		
		part learningModule {
			attribute learningRate : Real = 0.001;
			attribute memoryCapacity : Integer = 10000;
		}
		
		part decisionEngine {
			attribute responseTime : ISQ::TimeValue = 0.05[s];
		}
	}
	
	part def MotionControlSystem {
		port controlInput : ControlInputPort;
		port controlOutput : ActuatorPort;
		
		part inverseKinematics {
			attribute solverTolerance : ISQ::LengthValue = 0.001[m];
			attribute maxIterations : Integer = 100;
		}
		
		part motorController {
			attribute controlFrequency : ISQ::FrequencyValue = 1000[Hz];
			attribute pidGains : Real[3];
		}
		
		part trajectoryGenerator {
			attribute smoothingFactor : Real = 0.8;
		}
	}
	
	part def ManipulatorArm {
		port armControl : ActuatorPort;
		
		part shoulder {
			attribute shoulderAngle : JointAngle;
			attribute shoulderTorque : JointTorque;
			attribute mass : ISQ::MassValue = 2.5[kg];
		}
		
		part elbow {
			attribute elbowAngle : JointAngle;
			attribute elbowTorque : JointTorque;
			attribute mass : ISQ::MassValue = 1.8[kg];
		}
		
		part wrist {
			attribute wristAngle : JointAngle;
			attribute wristTorque : JointTorque;
			attribute mass : ISQ::MassValue = 0.9[kg];
		}
		
		part gripper {
			attribute gripForce : GripForce;
			attribute fingerPosition : ISQ::LengthValue;
			attribute maxGripForce : ISQ::ForceValue = 100[N];
			attribute mass : ISQ::MassValue = 0.6[kg];
		}
	}
	
	part def MobilitySystem {
		port mobilityControl : ActuatorPort;
		
		part leftLeg {
			part hip {
				attribute hipAngle : JointAngle;
				attribute hipTorque : JointTorque;
			}
			part knee {
				attribute kneeAngle : JointAngle;
				attribute kneeTorque : JointTorque;
			}
			part ankle {
				attribute ankleAngle : ISQ::AngleValue;
				attribute ankleTorque : JointTorque;
			}
		}
		
		part rightLeg {
			part hip {
				attribute hipAngle : JointAngle;
				attribute hipTorque : JointTorque;
			}
			part knee {
				attribute kneeAngle : JointAngle;
				attribute kneeTorque : JointTorque;
			}
			part ankle {
				attribute ankleAngle : ISQ::AngleValue;
				attribute ankleTorque : JointTorque;
			}
		}
		
		part balanceController {
			attribute stabilityThreshold : ISQ::AngleValue = 0.05[rad];
			attribute correctionGain : Real = 2.0;
		}
	}
	
	part def PowerSystem {
		attribute batteryCapacity : ISQ::EnergyValue = 2000[W*h];
		attribute currentCharge : ISQ::EnergyValue;
		attribute voltage : ISQ::ElectricPotentialValue = 48[V];
		attribute maxCurrent : ISQ::ElectricCurrentValue = 50[A];
	}
	
	action def PerceiveEnvironment {
		in sensorData : VisionData;
		in audioInput : AudioData;
		in tactileInput : TactileData;
		out environmentModel : EnvironmentModel;
	}
	
	action def PlanTask {
		in environment : EnvironmentModel;
		in instruction : TaskInstruction;
		out trajectory : MotionPlan;
		out safety : SafetyStatus;
	}
	
	action def ExecuteMotion {
		in plan : MotionPlan;
		in feedback : JointAngle[*];
		out commands : MotorCommand[*];
	}
	
	action def ManipulateObject {
		in objectLocation : EnvironmentModel;
		in graspStrategy : MotionPlan;
		out gripCommand : MotorCommand;
		out armCommands : MotorCommand[*];
	}
	
	action def Navigate {
		in targetLocation : EnvironmentModel;
		in currentPose : JointAngle[*];
		out walkingPattern : MotorCommand[*];
	}
	
	action def MonitorSafety {
		in environment : EnvironmentModel;
		in currentState : JointAngle[*];
		out safetyStatus : SafetyStatus;
	}
	
	action def AutonomousOperation {
		in sensorData : VisionData;
		in audioInput : AudioData;
		in tactileInput : TactileData;
		in instruction : TaskInstruction;
		in currentState : JointAngle[*];
		in feedback : JointAngle[*];
		out commands : MotorCommand[*];
		
		first start;
		then merge operationLoop;
		
		action perceive : PerceiveEnvironment {
			in sensorData = AutonomousOperation::sensorData;
			in audioInput = AutonomousOperation::audioInput;
			in tactileInput = AutonomousOperation::tactileInput;
			out environmentModel;
		}
		
		then action monitor : MonitorSafety {
			in environment = perceive.environmentModel;
			in currentState = AutonomousOperation::currentState;
			out safetyStatus;
		}
		
		then decide;
			if monitor.safetyStatus.isSafe then plan;
			if not monitor.safetyStatus.isSafe then emergencyStop;
		
		action plan : PlanTask {
			in environment = perceive.environmentModel;
			in instruction = AutonomousOperation::instruction;
			out trajectory;
			out safety;
		}
		
		then decide;
			if plan.trajectory.requiresManipulation then manipulate;
			if plan.trajectory.requiresNavigation then navigate;
			if plan.trajectory.isIdle then operationLoop;
		
		action manipulate : ManipulateObject {
			in objectLocation = perceive.environmentModel;
			in graspStrategy = plan.trajectory;
			out gripCommand;
			out armCommands;
		}
		then action executeManipulation : ExecuteMotion {
			in plan = plan.trajectory;
			in feedback = AutonomousOperation::feedback;
			out commands;
		}
		then operationLoop;
		
		action navigate : Navigate {
			in targetLocation = perceive.environmentModel;
			in currentPose = AutonomousOperation::currentState;
			out walkingPattern;
		}
		then action executeNavigation : ExecuteMotion {
			in plan = plan.trajectory;
			in feedback = AutonomousOperation::feedback;
			out commands;
		}
		then operationLoop;
		
		action emergencyStop : ExecuteMotion {
			in plan;
			in feedback = AutonomousOperation::feedback;
			out commands;
		}
		then done;
	}
	
	requirement def SafetyRequirement {
		doc /* The robot shall operate safely in human environments without causing harm to people or property. */
		
		require constraint collisionAvoidance {
			doc /* Maintain minimum safe distance of 0.1m from humans and obstacles during operation. */
		}
		
		require constraint forceLimit {
			doc /* Joint torques shall not exceed 80% of maximum rated torque. Grip forces shall not exceed 100N. */
		}
		
		require constraint emergencyStop {
			doc /* System shall halt all motion within 100ms upon detecting unsafe conditions. */
		}
	}
	
	requirement def PerformanceRequirement {
		doc /* The robot shall perform manipulation and mobility tasks with human-like dexterity and efficiency. */
		
		require constraint manipulationAccuracy {
			doc /* Object grasping shall achieve position accuracy within 5mm and orientation accuracy within 2 degrees. */
		}
		
		require constraint walkingSpeed {
			doc /* Walking speed shall reach 1.5 m/s on level surfaces with stable balance. */
		}
		
		require constraint batteryLife {
			doc /* Continuous operation shall be sustained for minimum 4 hours under typical workload. */
		}
		
		require constraint payloadCapacity {
			doc /* Each arm shall support lifting and manipulating objects up to 20kg mass. */
		}
	}
	
	requirement def AutonomyRequirement {
		doc /* The robot shall operate autonomously with minimal human intervention in diverse environments. */
		
		require constraint taskUnderstanding {
			doc /* System shall interpret natural language instructions with 95% accuracy for common tasks. */
		}
		
		require constraint adaptiveLearning {
			doc /* Performance shall improve through experience, reducing task completion time by 20% after 100 repetitions. */
		}
		
		require constraint environmentAdaptation {
			doc /* System shall adapt to new environments within 5 minutes of initial exposure. */
		}
	}
	
	requirement def PrimaryMission {
		doc /* The Figure AI humanoid robot shall autonomously perform general-purpose manipulation and mobility tasks in human-centric environments to assist with warehouse operations, manufacturing assembly, and service tasks. */
		
		assume constraint operatingEnvironment {
			doc /* Robot operates in structured indoor environments with temperatures between 10-35 degrees Celsius. */
		}
		
		require safetyReq : SafetyRequirement;
		require performanceReq : PerformanceRequirement;
		require autonomyReq : AutonomyRequirement;
	}
	
	part def HumanoidRobot {
		doc /* 
		A general-purpose humanoid robot capable of perceiving its environment through vision, audio, and tactile sensors,
		reasoning about tasks using AI-based cognition, and executing complex manipulation and mobility actions
		to assist humans in diverse real-world scenarios including warehouses, factories, and service environments.
		*/
		
		attribute height : ISQ::LengthValue = 1.68[m];
		attribute mass : ISQ::MassValue = 60[kg];
		attribute maxPayload : ISQ::MassValue = 20[kg];
		attribute operatingTemperature : ISQ::ThermodynamicTemperatureValue;
	}
	
	part figureRobot : HumanoidRobot {
		doc /* 
		Figure AI humanoid robot system designed to perform general-purpose tasks 
		in human environments through autonomous perception, cognition, and action.
		Primary function: Autonomously manipulate objects and navigate environments
		to complete warehouse logistics, assembly, and service tasks.
		*/
		
		port externalComm : CommunicationPort;
		
		part perceptionSys : PerceptionSystem {
			port sensors : SensorPort;
			port output : PerceptionOutputPort;
		}
		
		part cognitionSys : CognitionSystem {
			port input : CognitionInputPort;
			port output : CognitionOutputPort;
		}
		
		part motionControl : MotionControlSystem {
			port input : ControlInputPort;
			port output : ActuatorPort;
		}
		
		part leftArm : ManipulatorArm;
		part rightArm : ManipulatorArm;
		part mobilityBase : MobilitySystem;
		part powerSys : PowerSystem;
		
		connect perceptionSys.output.environmentModel to cognitionSys.input.environmentModel;
		connect externalComm.taskInstruction to cognitionSys.input.taskInstruction;
		connect cognitionSys.output.trajectoryPlan to motionControl.input.trajectoryPlan;
		connect motionControl.output to leftArm.armControl;
		connect motionControl.output to rightArm.armControl;
		connect motionControl.output to mobilityBase.mobilityControl;
		connect leftArm.armControl.jointAngle to motionControl.input.jointFeedback;
		connect rightArm.armControl.jointAngle to motionControl.input.jointFeedback;
		connect cognitionSys.output.safetyStatus to externalComm.safetyStatus;
		
		perform action autonomousOps : AutonomousOperation;
		
		satisfy primaryMission : PrimaryMission;
	}
}

// --- Test harness (auto-generated) ---
package ExecutionHarness {
    private import ScalarValues::*;
    private import ISQ::*;
    private import SI::*;
    private import 'Figure AI Humanoid Robot System'::*;

    action orchestrator {
        attribute testSensorData : VisionData;
        attribute testAudioInput : AudioData;
        attribute testTactileInput : TactileData;
        action perceiveProbe : PerceiveEnvironment {
            in sensorData = testSensorData;
            in audioInput = testAudioInput;
            in tactileInput = testTactileInput;
        }
        first perceiveProbe;
    }
}

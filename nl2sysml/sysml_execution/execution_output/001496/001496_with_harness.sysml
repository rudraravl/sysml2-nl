package MetamaterialCloakingSystem {
	private import ScalarValues::*;
	private import ISQ::*;
	private import SI::*;
	
	attribute def RefractiveIndex :> Real;
	
	attribute def Permittivity :> Real;
	
	attribute def Permeability :> Real;
	
	item def ElectromagneticWave {
		attribute frequency : FrequencyValue;
		attribute wavelength : LengthValue;
		attribute amplitude : Real;
		attribute polarization : Real[3];
		attribute propagationVector : Real[3];
	}
	
	item def MaterialProperties {
		attribute permittivity : Permittivity;
		attribute permeability : Permeability;
		attribute refractiveIndex : RefractiveIndex;
		attribute lossCoefficient : Real;
	}
	
	item def ControlCommand {
		attribute targetPermittivity : Permittivity;
		attribute targetPermeability : Permeability;
		attribute phaseShift : Real;
	}
	
	item def PowerOnCommand;
	item def ActivateCommand;
	item def DeactivateCommand;
	item def PowerOffCommand;
	
	port def EMInputPort {
		in item incidentWave : ElectromagneticWave;
	}
	
	port def EMOutputPort {
		out item transmittedWave : ElectromagneticWave;
		out item scatteredWave : ElectromagneticWave;
	}
	
	port def SensorPort {
		out item measuredWave : ElectromagneticWave;
	}
	
	port def ControlPort {
		in item command : ControlCommand;
	}
	
	port def PowerPort {
		in item powerLevel : PowerValue;
	}
	
	part def MetamaterialCell {
		attribute cellSize : LengthValue;
		attribute resonantFrequency : FrequencyValue;
		attribute properties : MaterialProperties;
		
		port input : EMInputPort;
		port output : EMOutputPort;
		port control : ControlPort;
		
		perform action modulateWave;
	}
	
	part def MetamaterialLayer {
		attribute layerThickness : LengthValue;
		attribute numberOfCells : Integer;
		
		part cells : MetamaterialCell[64];
		
		port layerInput : EMInputPort;
		port layerOutput : EMOutputPort;
		port layerControl : ControlPort;
	}
	
	part def WaveSensor {
		attribute sensitivity : Real;
		attribute detectionBandwidth : FrequencyValue;
		
		port waveInput : EMInputPort;
		port sensorOutput : SensorPort;
		
		perform action measureWave;
	}
	
	part def ControlProcessor {
		attribute processingRate : FrequencyValue;
		attribute targetRefractiveIndex : RefractiveIndex;
		
		port sensorInput : SensorPort;
		port controlOutput : ControlPort;
		port powerInput : PowerPort;
		
		perform action computeControl;
		perform action optimizeResponse;
	}
	
	part def PowerSupply {
		attribute outputVoltage : ElectricPotentialValue;
		attribute outputCurrent : ElectricCurrentValue;
		attribute capacity : EnergyValue;
		
		port powerOutput : PowerPort;
		
		perform action regulatePower;
	}
	
	action def MeasureElectromagneticWave {
		in wave : ElectromagneticWave;
		out measuredFrequency : FrequencyValue;
		out measuredAmplitude : Real;
		out measuredPhase : Real;
	}
	
	action def ComputeControlParameters {
		in measuredWave : ElectromagneticWave;
		in targetIndex : RefractiveIndex;
		out controlCmd : ControlCommand;
	}
	
	action def ModulateWaveProperties {
		in inputWave : ElectromagneticWave;
		in materialProps : MaterialProperties;
		in controlCmd : ControlCommand;
		out outputWave : ElectromagneticWave;
	}
	
	action def OptimizeCloakingResponse {
		in currentPerformance : Real;
		in targetPerformance : Real;
		out adjustmentFactor : Real;
	}
	
	state def CloakingSystemStates {
		entry; then powerOff;
		
		state powerOff {
			entry assign systemActive := false;
		}
		
		transition powerOff_to_initialization
			first powerOff
			accept PowerOnCommand
			then initialization;
		
		state initialization {
			entry; then calibrate;
			do action calibrate {
				out calibrationComplete : Boolean;
			}
		}
		
		transition initialization_to_standby
			first initialization
			if initialization.calibrate.calibrationComplete
			then standby;
		
		state standby {
			entry assign systemActive := true;
		}
		
		transition standby_to_activeCloaking
			first standby
			accept ActivateCommand
			then activeCloaking;
		
		state activeCloaking {
			entry; then sensing;
			
			state sensing {
				do action continuousSensing;
			}
			
			transition sensing_to_processing
				first sensing
				then processing;
			
			state processing {
				do action computeParameters;
			}
			
			transition processing_to_modulating
				first processing
				then modulating;
			
			state modulating {
				do action applyModulation;
			}
			
			transition modulating_to_verifying
				first modulating
				then verifying;
			
			state verifying {
				do action checkPerformance;
			}
			
			transition verifying_to_sensing
				first verifying
				if performanceAdequate
				then sensing;
			
			transition verifying_to_optimizing
				first verifying
				if not performanceAdequate
				then optimizing;
			
			state optimizing {
				do action adjustConfiguration;
			}
			
			transition optimizing_to_sensing
				first optimizing
				then sensing;
		}
		
		transition activeCloaking_to_standby
			first activeCloaking
			accept DeactivateCommand
			then standby;
		
		transition standby_to_powerOff
			first standby
			accept PowerOffCommand
			then powerOff;
		
		state performanceAdequate : Boolean;
		attribute systemActive : Boolean;
	}
	
	part metamaterialCloakingSystem {
		doc /* A metamaterial-based electromagnetic cloaking system that manipulates 
		       electromagnetic wave propagation to render objects invisible or reduce 
		       their radar cross-section by controlling the refractive index distribution 
		       around the target object. */
		
		attribute operatingFrequencyRange : FrequencyValue[2];
		attribute targetCloakingEfficiency : Real;
		attribute maximumObjectSize : LengthValue;
		
		part waveSensor : WaveSensor {
			attribute :>> sensitivity = 0.001;
			attribute :>> detectionBandwidth = 10.0e9;
			
			perform action measureWave : MeasureElectromagneticWave;
		}
		
		part layer0 : MetamaterialLayer;
		part layer1 : MetamaterialLayer;
		part layer2 : MetamaterialLayer;
		part layer3 : MetamaterialLayer;
		
		part controlProcessor : ControlProcessor {
			attribute :>> processingRate = 1.0e6;
			attribute :>> targetRefractiveIndex = -1.0;
			
			perform action computeControl : ComputeControlParameters;
			perform action optimizeResponse : OptimizeCloakingResponse;
			
			exhibit state systemStateMachine : CloakingSystemStates;
		}
		
		part powerSupply : PowerSupply {
			attribute :>> outputVoltage = 48.0;
			attribute :>> outputCurrent = 10.0;
			attribute :>> capacity = 5000.0;
			
			perform action regulatePower;
		}
		
		connection sensorToProcessor
			connect waveSensor.sensorOutput to controlProcessor.sensorInput;
		
		connection processorToMetamaterial
			connect controlProcessor.controlOutput to layer0.layerControl;
		
		connection powerToProcessor
			connect powerSupply.powerOutput to controlProcessor.powerInput;
		
		connection layerCascade1
			connect layer0.layerOutput to layer1.layerInput;
		
		connection layerCascade2
			connect layer1.layerOutput to layer2.layerInput;
		
		connection layerCascade3
			connect layer2.layerOutput to layer3.layerInput;
		
		connection sensorFeedback
			connect layer3.layerOutput to waveSensor.waveInput;
		
		perform action executeCloaking {
			first start;
			
			then action measureIncident : MeasureElectromagneticWave {
				in wave;
				out measuredFrequency;
				out measuredAmplitude;
				out measuredPhase;
			}
			
			then action computeControl : ComputeControlParameters {
				in measuredWave;
				in targetIndex = controlProcessor.targetRefractiveIndex;
				out controlCmd;
			}
			
			then action modulateLayer1 : ModulateWaveProperties {
				in inputWave = measureIncident.wave;
				in materialProps;
				in controlCmd = computeControl.controlCmd;
				out outputWave;
			}
			
			then action modulateLayer2 : ModulateWaveProperties {
				in inputWave = modulateLayer1.outputWave;
				in materialProps;
				in controlCmd = computeControl.controlCmd;
				out outputWave;
			}
			
			then action modulateLayer3 : ModulateWaveProperties {
				in inputWave = modulateLayer2.outputWave;
				in materialProps;
				in controlCmd = computeControl.controlCmd;
				out outputWave;
			}
			
			then action modulateLayer4 : ModulateWaveProperties {
				in inputWave = modulateLayer3.outputWave;
				in materialProps;
				in controlCmd = computeControl.controlCmd;
				out outputWave;
			}
			
			then action verifyPerformance : MeasureElectromagneticWave {
				in wave = modulateLayer4.outputWave;
				out measuredFrequency;
				out measuredAmplitude;
				out measuredPhase;
			}
			
			then decide;
				if verifyPerformance.measuredAmplitude < 0.1 then maintainCloaking;
				if verifyPerformance.measuredAmplitude >= 0.1 then optimizeSystem;
			
			action optimizeSystem : OptimizeCloakingResponse {
				in currentPerformance = verifyPerformance.measuredAmplitude;
				in targetPerformance = 0.05;
				out adjustmentFactor;
			}
			then start;
			
			action maintainCloaking;
			then done;
		}
	}
	
	requirement def SystemPerformanceRequirement {
		doc /* The metamaterial cloaking system shall manipulate electromagnetic wave 
		       propagation to achieve specified cloaking performance metrics. */
		
		require constraint cloakingEfficiency {
			doc /* The system shall reduce the radar cross-section by at least 90% 
			       within the operating frequency range. */
		}
		
		require constraint frequencyBandwidth {
			doc /* The system shall operate across a frequency bandwidth of at least 
			       5 GHz centered at 10 GHz. */
		}
		
		require constraint responseTime {
			doc /* The system shall adapt to changing electromagnetic conditions 
			       within 100 microseconds. */
		}
	}
	
	requirement <'REQ-META-001'> cloakingSystemRequirement : SystemPerformanceRequirement {
		subject metamaterialCloakingSystem;
		
		assume constraint operatingEnvironment {
			doc /* The system operates in controlled environmental conditions with 
			       ambient temperature between 15°C and 35°C. */
		}
		
		require constraint cloakingEfficiency {
			attribute radarCrossSection : Real;
			radarCrossSection <= 0.1
		}
		
		require constraint frequencyBandwidth {
			attribute minFrequency : FrequencyValue;
			attribute maxFrequency : FrequencyValue;
			minFrequency >= 7.5e9 and maxFrequency <= 12.5e9
		}
		
		require constraint responseTime {
			attribute adaptationTime : DurationValue;
			adaptationTime <= 100.0e-6
		}
	}
	
	requirement functionalRequirement {
		doc /* The metamaterial cloaking system shall control electromagnetic wave 
		       propagation by dynamically adjusting the refractive index distribution 
		       through engineered metamaterial structures to achieve electromagnetic 
		       cloaking of objects within the specified frequency range. */
		
		require cloakingSystemRequirement;
	}
}

// --- Test harness (auto-generated) ---
package ExecutionHarness {
    private import ScalarValues::*;
    private import ISQ::*;
    private import SI::*;
    private import MetamaterialCloakingSystem::*;

    part testSubject = metamaterialCloakingSystem {
    :>> currentPerformance = 0.0;
    :>> targetPerformance = 0.0;
    }

    part controlProcessor : MetamaterialCell {
        exhibit state sm : CloakingSystemStates;
    }

    action orchestrator {
        item testPowerOnCommand : PowerOnCommand;
        item testActivateCommand : ActivateCommand;
        item testDeactivateCommand : DeactivateCommand;
        action triggerPowerOnCommand send testPowerOnCommand to controlProcessor;
        action triggerActivateCommand send testActivateCommand to controlProcessor;
        action triggerDeactivateCommand send testDeactivateCommand to controlProcessor;
        first triggerPowerOnCommand;
        then triggerActivateCommand;
        then triggerDeactivateCommand;
    }
}

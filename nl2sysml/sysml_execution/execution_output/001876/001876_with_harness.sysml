package TaccolaHydraulicSystem {
    private import ScalarValues::*;
    private import ISQ::*;
    private import SI::*;
    
    attribute def WaterFlowRate :> ISQ::VolumeValue {
        doc /* Rate of water volume flowing per unit time */
    }
    
    attribute def RotationalSpeed :> ISQ::AngularVelocityValue {
        doc /* Angular velocity of rotating components */
    }
    
    attribute def WaterLevel :> ISQ::LengthValue {
        doc /* Vertical height of water surface */
    }
    
    attribute def TorqueOutput :> ISQ::TorqueValue {
        doc /* Rotational force generated by mechanical components */
    }
    
    attribute def WaterPressure :> ISQ::PressureValue {
        doc /* Force per unit area exerted by water */
    }
    
    attribute def LiftHeight :> ISQ::LengthValue {
        doc /* Vertical distance a load is raised */
    }
    
    port def WaterInletPort {
        in attribute flowRate : WaterFlowRate;
        in attribute pressure : WaterPressure;
    }
    
    port def WaterOutletPort {
        out attribute flowRate : WaterFlowRate;
        out attribute pressure : WaterPressure;
    }
    
    port def MechanicalPowerPort {
        out attribute torque : TorqueOutput;
        out attribute rotationalSpeed : RotationalSpeed;
    }
    
    part def UpperReservoir {
        doc /* Storage basin that accumulates water from supply source */
        attribute capacity : ISQ::VolumeValue;
        attribute currentLevel : WaterLevel;
        attribute maxLevel : WaterLevel;
        port waterInlet : WaterInletPort;
        port waterOutlet : WaterOutletPort;
    }
    
    part def OverflowSiphon {
        doc /* Automatic release mechanism triggered by water level threshold */
        attribute activationLevel : WaterLevel;
        attribute siphonDiameter : ISQ::LengthValue;
        port waterInput : WaterInletPort;
        port waterDischarge : WaterOutletPort;
    }
    
    part def UndershotWaterWheel {
        doc /* Rotating wheel driven by water flow impacting lower buckets */
        attribute wheelDiameter : ISQ::LengthValue;
        attribute wheelWidth : ISQ::LengthValue;
        attribute numberOfBuckets : ScalarValues::Integer;
        attribute bucketVolume : ISQ::VolumeValue;
        port waterInput : WaterInletPort;
        port waterOutput : WaterOutletPort;
        port mechanicalOutput : MechanicalPowerPort;
    }
    
    part def AxleShaft {
        doc /* Central rotating shaft transmitting torque from wheel */
        attribute shaftLength : ISQ::LengthValue;
        attribute shaftDiameter : ISQ::LengthValue;
        attribute material : ScalarValues::String;
        port mechanicalInput : MechanicalPowerPort;
        port mechanicalOutput : MechanicalPowerPort;
    }
    
    part def CrankMechanism {
        doc /* Converts rotational motion to reciprocating linear motion */
        attribute crankRadius : ISQ::LengthValue;
        attribute strokeLength : ISQ::LengthValue;
        port mechanicalInput : MechanicalPowerPort;
    }
    
    part def PumpingBellows {
        doc /* Reciprocating pump driven by crank for water lifting */
        attribute bellowsCapacity : ISQ::VolumeValue;
        attribute maxPumpHeight : LiftHeight;
        port waterIntake : WaterInletPort;
        port waterDelivery : WaterOutletPort;
    }
    
    action def AccumulateWater {
        doc /* Fill reservoir from water source until threshold reached */
        in supplyFlowRate : WaterFlowRate;
        in currentLevel : WaterLevel;
        in reservoirCapacity : ISQ::VolumeValue;
        in deltaTime : ISQ::TimeValue;
        out newLevel : WaterLevel;
    }
    
    action def CheckOverflowCondition {
        doc /* Determine if water level exceeds siphon activation threshold */
        in waterLevel : WaterLevel;
        in activationThreshold : WaterLevel;
        out overflowTriggered : ScalarValues::Boolean;
    }
    
    action def ActivateSiphon {
        doc /* Release accumulated water through overflow mechanism */
        in reservoirLevel : WaterLevel;
        in siphonDiameter : ISQ::LengthValue;
        out dischargeFlowRate : WaterFlowRate;
        out dischargePressure : WaterPressure;
    }
    
    action def DriveWaterWheel {
        doc /* Convert water flow energy into rotational mechanical energy */
        in incomingFlowRate : WaterFlowRate;
        in incomingPressure : WaterPressure;
        in wheelDiameter : ISQ::LengthValue;
        in bucketCount : ScalarValues::Integer;
        out wheelSpeed : RotationalSpeed;
        out outputTorque : TorqueOutput;
    }
    
    action def TransmitTorque {
        doc /* Transfer rotational power through shaft with minimal loss */
        in inputTorque : TorqueOutput;
        in inputSpeed : RotationalSpeed;
        in shaftEfficiency : ScalarValues::Real;
        out outputTorque : TorqueOutput;
        out outputSpeed : RotationalSpeed;
    }
    
    action def ConvertToCrankMotion {
        doc /* Transform continuous rotation into reciprocating motion */
        in rotationalTorque : TorqueOutput;
        in rotationalSpeed : RotationalSpeed;
        in crankRadius : ISQ::LengthValue;
        out strokeFrequency : ISQ::FrequencyValue;
        out linearForce : ISQ::ForceValue;
    }
    
    action def PumpWater {
        doc /* Lift water from lower source to elevated destination */
        in strokeFrequency : ISQ::FrequencyValue;
        in bellowsVolume : ISQ::VolumeValue;
        in targetHeight : LiftHeight;
        out pumpedFlowRate : WaterFlowRate;
        out deliveryPressure : WaterPressure;
    }
    
    action def OperateTaccolaHydraulicCycle {
        doc /* Complete operational cycle from water accumulation to pumping */
        first start;
        then merge continuousOperation;
        then action accumulate : AccumulateWater {
            in supplyFlowRate;
            in currentLevel;
            in reservoirCapacity;
            in deltaTime;
            out newLevel;
        }
        then action checkOverflow : CheckOverflowCondition {
            in waterLevel = accumulate.newLevel;
            in activationThreshold;
            out overflowTriggered;
        }
        then decide;
            if checkOverflow.overflowTriggered then activateSiphon;
            if !checkOverflow.overflowTriggered then continuousOperation;
        action activateSiphon : ActivateSiphon {
            in reservoirLevel = accumulate.newLevel;
            in siphonDiameter;
            out dischargeFlowRate;
            out dischargePressure;
        }
        then action driveWheel : DriveWaterWheel {
            in incomingFlowRate = activateSiphon.dischargeFlowRate;
            in incomingPressure = activateSiphon.dischargePressure;
            in wheelDiameter;
            in bucketCount;
            out wheelSpeed;
            out outputTorque;
        }
        then action transmit : TransmitTorque {
            in inputTorque = driveWheel.outputTorque;
            in inputSpeed = driveWheel.wheelSpeed;
            in shaftEfficiency;
            out outputTorque;
            out outputSpeed;
        }
        then action convertMotion : ConvertToCrankMotion {
            in rotationalTorque = transmit.outputTorque;
            in rotationalSpeed = transmit.outputSpeed;
            in crankRadius;
            out strokeFrequency;
            out linearForce;
        }
        then action pump : PumpWater {
            in strokeFrequency = convertMotion.strokeFrequency;
            in bellowsVolume;
            in targetHeight;
            out pumpedFlowRate;
            out deliveryPressure;
        }
        then continuousOperation;
    }
    
    attribute def WaterSupplyConnected;
    attribute def SystemShutdown;
    
    state def TaccolaOperationalStates {
        doc /* State machine governing system operational modes */
        entry; then idle;
        
        state idle {
            doc /* System at rest awaiting water supply */
            entry assign systemActive := false;
        }
        
        transition idle_to_filling
            first idle
            accept WaterSupplyConnected
            then filling;
        
        state filling {
            doc /* Reservoir accumulating water from source */
            entry action beginFilling : AccumulateWater;
            do action monitorLevel : CheckOverflowCondition;
        }
        
        transition filling_to_overflowing
            first filling
            if currentWaterLevel >= siphonActivationLevel
            then overflowing;
        
        state overflowing {
            doc /* Siphon releasing water to drive wheel */
            entry action initiateDischarge : ActivateSiphon;
            do action maintainFlow : DriveWaterWheel;
        }
        
        transition overflowing_to_operating
            first overflowing
            if wheelRotationalSpeed > minimumOperatingSpeed
            then operating;
        
        state operating {
            doc /* Full system operation with active pumping */
            do action performPumping : PumpWater;
            do action transmitPower : TransmitTorque;
        }
        
        transition operating_to_filling
            first operating
            if currentWaterLevel < siphonActivationLevel
            then filling;
        
        transition operating_to_idle
            first operating
            accept SystemShutdown
            then idle;
        
        attribute systemActive : ScalarValues::Boolean;
        attribute currentWaterLevel : WaterLevel;
        attribute siphonActivationLevel : WaterLevel;
        attribute wheelRotationalSpeed : RotationalSpeed;
        attribute minimumOperatingSpeed : RotationalSpeed;
    }
    
    part def TaccolaHydraulicSystemDef {
        doc /* 
            A Taccola hydraulic system is an automated water-powered machine 
            that uses gravity-driven overflow to generate continuous mechanical 
            power for pumping operations. Water accumulates in an upper reservoir 
            until reaching a critical level, triggering an automatic siphon that 
            releases the stored water onto an undershot wheel. The rotating wheel 
            drives a crank mechanism that operates reciprocating bellows pumps, 
            lifting water from a lower source to an elevated destination. This 
            represents a self-regulating hydraulic engine requiring no external 
            power source beyond the initial water supply and gravity.
        */
        
        part upperReservoir : UpperReservoir {
            attribute :>> capacity = 8.0[m^3];
            attribute :>> currentLevel = 0.0[m];
            attribute :>> maxLevel = 3.5[m];
        }
        
        part overflowSiphon : OverflowSiphon {
            attribute :>> activationLevel = 3.0[m];
            attribute :>> siphonDiameter = 0.25[m];
        }
        
        part waterWheel : UndershotWaterWheel {
            attribute :>> wheelDiameter = 4.0[m];
            attribute :>> wheelWidth = 1.2[m];
            attribute :>> numberOfBuckets = 32;
            attribute :>> bucketVolume = 0.08[m^3];
        }
        
        part axleShaft : AxleShaft {
            attribute :>> shaftLength = 2.5[m];
            attribute :>> shaftDiameter = 0.20[m];
            attribute :>> material = "oak";
        }
        
        part crankMechanism : CrankMechanism {
            attribute :>> crankRadius = 0.30[m];
            attribute :>> strokeLength = 0.60[m];
        }
        
        part pumpingBellows : PumpingBellows {
            attribute :>> bellowsCapacity = 0.15[m^3];
            attribute :>> maxPumpHeight = 8.0[m];
        }
        
        connect upperReservoir.waterOutlet to overflowSiphon.waterInput;
        connect overflowSiphon.waterDischarge to waterWheel.waterInput;
        connect waterWheel.mechanicalOutput to axleShaft.mechanicalInput;
        connect axleShaft.mechanicalOutput to crankMechanism.mechanicalInput;
        
        perform action operateCycle : OperateTaccolaHydraulicCycle {
            in supplyFlowRate = 0.05[m^3];
            in currentLevel = upperReservoir.currentLevel;
            in reservoirCapacity = upperReservoir.capacity;
            in deltaTime = 1.0[s];
            in activationThreshold = overflowSiphon.activationLevel;
            in siphonDiameter = overflowSiphon.siphonDiameter;
            in wheelDiameter = waterWheel.wheelDiameter;
            in bucketCount = waterWheel.numberOfBuckets;
            in shaftEfficiency = 0.85;
            in crankRadius = crankMechanism.crankRadius;
            in bellowsVolume = pumpingBellows.bellowsCapacity;
            in targetHeight = pumpingBellows.maxPumpHeight;
        }
        
        exhibit state systemStates : TaccolaOperationalStates {
            :>> siphonActivationLevel = overflowSiphon.activationLevel;
            :>> minimumOperatingSpeed = 0.5[rad/s];
        }
    }
    
    part taccolaSystem : TaccolaHydraulicSystemDef;
    
    requirement def AutomaticOperationRequirement {
        doc /* System shall operate autonomously without manual intervention */
        subject system : TaccolaHydraulicSystemDef;
        require constraint {
            system.overflowSiphon.activationLevel < system.upperReservoir.maxLevel
        }
    }
    
    requirement def ContinuousPumpingRequirement {
        doc /* System shall maintain continuous pumping when water supply is available */
        subject system : TaccolaHydraulicSystemDef;
        require constraint {
            system.pumpingBellows.maxPumpHeight >= 5.0[m]
        }
    }
    
    requirement def MechanicalEfficiencyRequirement {
        doc /* System shall convert hydraulic energy to mechanical work efficiently */
        subject wheel : UndershotWaterWheel;
        require constraint {
            wheel.mechanicalOutput.torque > 200.0[N*m]
        }
    }
    
    requirement def ReservoirCapacityRequirement {
        doc /* Reservoir shall store sufficient water for sustained operation cycles */
        subject reservoir : UpperReservoir;
        require constraint {
            reservoir.capacity >= 6.0[m^3]
        }
    }
    
    requirement def SiphonActivationRequirement {
        doc /* Overflow siphon shall activate at predetermined water level threshold */
        subject siphon : OverflowSiphon;
        require constraint {
            siphon.activationLevel >= 2.5[m] and siphon.activationLevel <= 3.5[m]
        }
    }
    
    requirement taccolaSystemRequirements {
        doc /* Comprehensive requirements for Taccola hydraulic system operation */
        subject taccolaSystem;
        
        assume constraint {
            taccolaSystem.overflowSiphon.activationLevel < taccolaSystem.upperReservoir.maxLevel
        }
        
        require constraint {
            taccolaSystem.pumpingBellows.maxPumpHeight >= 5.0[m]
        }
        
        require constraint {
            taccolaSystem.waterWheel.mechanicalOutput.torque > 200.0[N*m]
        }
        
        require constraint {
            taccolaSystem.upperReservoir.capacity >= 6.0[m^3]
        }
        
        require constraint {
            taccolaSystem.overflowSiphon.activationLevel >= 2.5[m] and 
            taccolaSystem.overflowSiphon.activationLevel <= 3.5[m]
        }
    }
}

// --- Test harness (auto-generated) ---
package ExecutionHarness {
    private import ScalarValues::*;
    private import ISQ::*;
    private import SI::*;
    private import TaccolaHydraulicSystem::*;

    part testSubject : TaccolaHydraulicSystemDef {
        exhibit state systemStates : TaccolaOperationalStates;
    }

    action orchestrator {
        attribute testReservoirLevel : WaterLevel;
        attribute testSiphonDiameter : ISQ::LengthValue;
        action activateSiphonProbe : ActivateSiphon {
            in reservoirLevel = testReservoirLevel;
            in siphonDiameter = testSiphonDiameter;
        }
        attribute testWaterSupplyConnected : WaterSupplyConnected;
        attribute testSystemShutdown : SystemShutdown;
        action triggerWaterSupplyConnected send testWaterSupplyConnected to testSubject.systemStates;
        action triggerSystemShutdown send testSystemShutdown to testSubject.systemStates;
        first activateSiphonProbe;
        then triggerWaterSupplyConnected;
        then triggerSystemShutdown;
    }
}

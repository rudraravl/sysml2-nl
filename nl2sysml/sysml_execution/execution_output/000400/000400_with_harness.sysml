package AmazonScoutDeliverySystem {
    private import ISQ::*;
    private import SI::*;
    private import ScalarValues::*;
    
    attribute def GPSCoordinate {
        attribute latitude : Real;
        attribute longitude : Real;
        attribute altitude : LengthValue;
    }
    
    attribute def DeliveryAddress {
        attribute street : String;
        attribute city : String;
        attribute zipCode : String;
        attribute gpsLocation : GPSCoordinate;
    }
    
    attribute def PackageID;
    attribute def CustomerID;
    attribute def ObstacleDetected;
    attribute def DeliveryConfirmation;
    attribute def MissionStart;
    attribute def MissionComplete;
    
    item def Package {
        attribute packageID : PackageID;
        attribute customerID : CustomerID;
        attribute destination : DeliveryAddress;
        attribute weight : MassValue;
        attribute dimensions : LengthValue[3];
        attribute isFragile : Boolean;
    }
    
    item def ObstacleData {
        attribute distance : LengthValue;
        attribute bearing : Real;
        attribute relativeVelocity : SpeedValue;
        attribute obstacleType : String;
    }
    
    item def NavigationData {
        attribute currentPosition : GPSCoordinate;
        attribute currentHeading : Real;
        attribute currentSpeed : SpeedValue;
        attribute targetWaypoint : GPSCoordinate;
    }
    
    item def SensorData {
        attribute obstacles : ObstacleData[*];
        attribute navigationInfo : NavigationData;
        attribute batteryLevel : Real;
    }
    
    item def ControlCommand {
        attribute targetSpeed : SpeedValue;
        attribute targetHeading : Real;
        attribute brakeCommand : Boolean;
    }
    
    port def PowerPort {
        attribute voltage : ElectricPotentialValue;
        attribute current : ElectricCurrentValue;
    }
    
    port def DataPort {
        in item sensorInput;
        out item controlOutput;
    }
    
    port def CargoPort {
        in item packageLoad : Package;
        out item packageUnload : Package;
    }
    
    part def LidarSensor {
        attribute scanRange : LengthValue;
        attribute scanRate : FrequencyValue;
        attribute angularResolution : Real;
        port dataOut : DataPort;
        
        action def PerformScan {
            out obstacleMap : ObstacleData[*];
            out scanQuality : Real;
        }
    }
    
    part def CameraSystem {
        attribute resolution : String;
        attribute frameRate : FrequencyValue;
        attribute fieldOfView : Real;
        port imageDataOut : DataPort;
        
        action def CaptureFrame {
            out imageData;
            out detectedObjects : String[*];
        }
    }
    
    part def GPSReceiver {
        attribute positionAccuracy : LengthValue;
        port positionOut : DataPort;
        
        action def GetPosition {
            out position : GPSCoordinate;
            out accuracy : LengthValue;
        }
    }
    
    part def IMU {
        attribute gyroRange : Real;
        attribute accelRange : AccelerationValue;
        port motionDataOut : DataPort;
        
        action def MeasureMotion {
            out orientation : Real[3];
            out acceleration : AccelerationValue[3];
        }
    }
    
    part def AutonomyController {
        attribute processingPower : String;
        port sensorDataIn : DataPort;
        port commandOut : DataPort;
        
        action def ProcessSensorData {
            in sensorData : SensorData;
            out worldModel;
        }
        
        action def PlanPath {
            in currentPos : GPSCoordinate;
            in targetPos : GPSCoordinate;
            in obstacles : ObstacleData[*];
            out waypoints : GPSCoordinate[*];
            out pathCost : Real;
        }
        
        action def GenerateControl {
            in waypoints : GPSCoordinate[*];
            in currentState : NavigationData;
            out command : ControlCommand;
        }
    }
    
    part def DriveMotor {
        attribute maxTorque : TorqueValue;
        attribute maxSpeed : Real;
        port powerIn : PowerPort;
        port controlIn : DataPort;
        
        action def ApplyTorque {
            in commandedTorque : TorqueValue;
            out actualTorque : TorqueValue;
        }
    }
    
    part def SteeringActuator {
        attribute maxSteeringAngle : Real;
        attribute responseTime : TimeValue;
        port powerIn : PowerPort;
        port controlIn : DataPort;
        
        action def SetSteeringAngle {
            in targetAngle : Real;
            out actualAngle : Real;
        }
    }
    
    part def BrakingSystem {
        attribute maxBrakingForce : ForceValue;
        port powerIn : PowerPort;
        port controlIn : DataPort;
        
        action def ApplyBrake {
            in brakeCommand : Boolean;
            in brakingForce : ForceValue;
            out actualForce : ForceValue;
        }
    }
    
    part def BatteryPack {
        attribute capacity : EnergyValue;
        attribute nominalVoltage : ElectricPotentialValue;
        attribute currentCharge : EnergyValue;
        attribute stateOfCharge : Real;
        port powerOut : PowerPort;
        
        action def SupplyPower {
            in powerDemand : PowerValue;
            in duration : TimeValue;
            out energyDelivered : EnergyValue;
            out remainingCharge : EnergyValue;
        }
    }
    
    part def SecureCargoCompartment {
        attribute maxPayloadMass : MassValue;
        attribute currentPayloadMass : MassValue;
        attribute isLocked : Boolean;
        attribute temperatureControlled : Boolean;
        port cargoAccess : CargoPort;
        
        action def LoadPackage {
            in pkg : Package;
            out loadSuccess : Boolean;
            out compartmentLocked : Boolean;
        }
        
        action def UnloadPackage {
            in authorizationCode : String;
            out pkg : Package;
            out unloadSuccess : Boolean;
        }
        
        action def VerifyDelivery {
            in customerID : CustomerID;
            out verified : Boolean;
        }
    }
    
    part def WirelessCommunication {
        attribute frequency : FrequencyValue;
        attribute bandwidth : FrequencyValue;
        attribute signalStrength : Real;
        port dataLink : DataPort;
        
        action def TransmitTelemetry {
            in telemetryData;
            out transmitSuccess : Boolean;
        }
        
        action def ReceiveMission {
            out missionData : Package;
            out receiveSuccess : Boolean;
        }
    }
    
    part def AmazonScout {
        attribute vehicleID : String;
        attribute maxOperatingSpeed : SpeedValue;
        attribute operationalRange : LengthValue;
        attribute currentMissionStatus : String;
        
        part perceptionSystem {
            part frontLidar : LidarSensor {
                attribute scanRange = 30.0 [SI::m];
                attribute scanRate = 10.0 [SI::Hz];
                attribute angularResolution = 0.25;
            }
            part rearLidar : LidarSensor {
                attribute scanRange = 15.0 [SI::m];
                attribute scanRate = 10.0 [SI::Hz];
                attribute angularResolution = 0.5;
            }
            part frontCamera : CameraSystem {
                attribute resolution = "1920x1080";
                attribute frameRate = 30.0 [SI::Hz];
                attribute fieldOfView = 120.0;
            }
            part sideCamera : CameraSystem[2] {
                attribute resolution = "1280x720";
                attribute frameRate = 30.0 [SI::Hz];
                attribute fieldOfView = 90.0;
            }
            part gps : GPSReceiver {
                attribute positionAccuracy = 0.5 [SI::m];
            }
            part imu : IMU {
                attribute gyroRange = 500.0;
                attribute accelRange = 16.0 [SI::'m/s^2'];
            }
        }
        
        part autonomy : AutonomyController {
            attribute processingPower = "NVIDIA Jetson Xavier";
        }
        
        part mobilitySystem {
            part leftDriveMotor : DriveMotor {
                attribute maxTorque = 50.0 [SI::'N*m'];
                attribute maxSpeed = 300.0;
            }
            part rightDriveMotor : DriveMotor {
                attribute maxTorque = 50.0 [SI::'N*m'];
                attribute maxSpeed = 300.0;
            }
            part steering : SteeringActuator {
                attribute maxSteeringAngle = 45.0;
                attribute responseTime = 0.2 [SI::s];
            }
            part brakes : BrakingSystem {
                attribute maxBrakingForce = 500.0 [SI::N];
            }
        }
        
        part powerSystem : BatteryPack {
            attribute capacity = 2000.0 [SI::J];
            attribute nominalVoltage = 48.0 [SI::V];
            attribute currentCharge = 2000.0 [SI::J];
            attribute stateOfCharge = 1.0;
        }
        
        part cargo : SecureCargoCompartment {
            attribute maxPayloadMass = 25.0 [SI::kg];
            attribute currentPayloadMass = 0.0 [SI::kg];
            attribute isLocked = true;
            attribute temperatureControlled = true;
        }
        
        part communications : WirelessCommunication {
            attribute frequency = 2.4e9 [SI::Hz];
            attribute bandwidth = 20.0e6 [SI::Hz];
            attribute signalStrength = 0.9;
        }
        
        connection powerToMotors : PowerPort connect powerSystem.powerOut to mobilitySystem.leftDriveMotor.powerIn;
        connection powerToSteering : PowerPort connect powerSystem.powerOut to mobilitySystem.steering.powerIn;
        connection powerToBrakes : PowerPort connect powerSystem.powerOut to mobilitySystem.brakes.powerIn;
        connection sensorToAutonomy : DataPort connect perceptionSystem.frontLidar.dataOut to autonomy.sensorDataIn;
        connection autonomyToMotors : DataPort connect autonomy.commandOut to mobilitySystem.leftDriveMotor.controlIn;
        
        perform action executeDeliveryMission[*] ordered references autonomousDeliveryBehavior;
    }
    
    action def ScanEnvironment {
        in lidarData : ObstacleData[*];
        in cameraData;
        out environmentModel;
        out safetyAssessment : Boolean;
    }
    
    action def LocalizeVehicle {
        in gpsPosition : GPSCoordinate;
        in imuData;
        in environmentModel;
        out estimatedPose : NavigationData;
    }
    
    action def PlanDeliveryRoute {
        in startLocation : GPSCoordinate;
        in deliveryDestination : DeliveryAddress;
        in environmentModel;
        out routePlan : GPSCoordinate[*];
        out estimatedDuration : TimeValue;
    }
    
    action def ExecuteNavigation {
        in routePlan : GPSCoordinate[*];
        in currentPose : NavigationData;
        in obstacles : ObstacleData[*];
        out controlCommands : ControlCommand;
        out navigationStatus : String;
    }
    
    action def PerformObstacleAvoidance {
        in detectedObstacle : ObstacleData;
        in currentVelocity : SpeedValue;
        in currentHeading : Real;
        out evasiveManeuver : ControlCommand;
    }
    
    action def AuthenticateDelivery {
        in customerID : CustomerID;
        in deliveryLocation : GPSCoordinate;
        out authenticationSuccess : Boolean;
        out unlockCode : String;
    }
    
    action def CompleteDelivery {
        in package : Package;
        in unlockCode : String;
        out deliveryConfirmation;
        out packageReleased : Boolean;
    }
    
    action autonomousDeliveryBehavior : AutonomousDeliveryMission {
        first start;
        
        then action receiveMission {
            out assignedPackage : Package;
            out deliveryTarget : DeliveryAddress;
        }
        
        then action loadCargo {
            in pkg = receiveMission.assignedPackage;
            out cargoSecured : Boolean;
            out compartmentLocked : Boolean;
        }
        
        then action planRoute : PlanDeliveryRoute {
            in startLocation;
            in deliveryDestination = receiveMission.deliveryTarget.gpsLocation;
            out route : GPSCoordinate[*];
            out eta : TimeValue;
        }
        
        then merge navigationCycle;
        
        action navigationCycle {
            action scanSurroundings : ScanEnvironment {
                out envModel;
                out isSafe : Boolean;
            }
            
            then action localize : LocalizeVehicle {
                in environmentModel = scanSurroundings.envModel;
                out pose : NavigationData;
            }
            
            then decide;
                if scanSurroundings.isSafe then navigateNormally;
                if not scanSurroundings.isSafe then handleObstacle;
            
            action navigateNormally : ExecuteNavigation {
                in routePlan = planRoute.route;
                in currentPose = localize.pose;
                out commands : ControlCommand;
                out status : String;
            }
            
            then decide;
                if navigateNormally.status == "arrived" then proceedToDelivery;
                if navigateNormally.status == "navigating" then navigationCycle;
            
            action handleObstacle {
                action detectObstacleDetails {
                    out obstacleInfo : ObstacleData;
                }
                
                then action computeEvasion : PerformObstacleAvoidance {
                    in detectedObstacle = detectObstacleDetails.obstacleInfo;
                    out evasiveAction : ControlCommand;
                }
                
                then action executeEvasion {
                    in maneuver = computeEvasion.evasiveAction;
                }
            }
            then navigationCycle;
        }
        
        action proceedToDelivery {
            action notifyCustomer {
                out notificationSent : Boolean;
            }
            
            then action waitForCustomer {
                out customerPresent : Boolean;
            }
            
            then action authenticate : AuthenticateDelivery {
                in customerID = receiveMission.assignedPackage.customerID;
                out authSuccess : Boolean;
                out code : String;
            }
            
            then action deliver : CompleteDelivery {
                in package = receiveMission.assignedPackage;
                in unlockCode = authenticate.code;
                out confirmation;
                out released : Boolean;
            }
        }
        
        then action transmitConfirmation {
            in deliveryData = proceedToDelivery.deliver.confirmation;
            out transmitSuccess : Boolean;
        }
        
        then action returnToDepot {
            in depotLocation : GPSCoordinate;
            out returnStatus : String;
        }
        
        then done;
    }
    
    requirement def SafetyRequirement {
        doc /* The autonomous delivery robot shall detect and avoid obstacles 
               to ensure safe operation in pedestrian and urban environments. */
        
        subject scout : AmazonScout;
        
        require constraint minimumDetectionRange {
            scout.perceptionSystem.frontLidar.scanRange >= 20.0 [SI::m]
        }
        
        require constraint maximumOperatingSpeed {
            scout.maxOperatingSpeed <= 2.5 [SI::'m/s']
        }
        
        require constraint emergencyBraking {
            scout.mobilitySystem.brakes.maxBrakingForce >= 400.0 [SI::N]
        }
    }
    
    requirement def PayloadRequirement {
        doc /* The delivery robot shall securely transport packages up to 
               specified weight limits while maintaining package integrity. */
        
        subject scout : AmazonScout;
        
        require constraint payloadCapacity {
            scout.cargo.maxPayloadMass >= 22.0 [SI::kg]
        }
        
        require constraint secureStorage {
            scout.cargo.isLocked == true
        }
    }
    
    requirement def AutonomyRequirement {
        doc /* The robot shall navigate autonomously using multi-sensor fusion 
               and real-time path planning without human intervention. */
        
        subject scout : AmazonScout;
        
        require constraint sensorRedundancy {
            scout.perceptionSystem.frontLidar->size() >= 1 and
            scout.perceptionSystem.frontCamera->size() >= 1
        }
        
        require constraint positionAccuracy {
            scout.perceptionSystem.gps.positionAccuracy <= 1.0 [SI::m]
        }
    }
    
    requirement def EnduranceRequirement {
        doc /* The robot shall operate for sufficient duration to complete 
               typical delivery routes on a single charge. */
        
        subject scout : AmazonScout;
        
        require constraint batteryCapacity {
            scout.powerSystem.capacity >= 1500.0 [SI::J]
        }
        
        require constraint operationalRange {
            scout.operationalRange >= 25.0 [SI::km]
        }
    }
    
    requirement <'SCOUT-MISSION-001'> primaryDeliveryMission {
        doc /* Amazon Scout shall autonomously deliver packages from distribution 
               centers to customer doorsteps in residential neighborhoods, 
               navigating sidewalks and streets while avoiding obstacles, 
               maintaining secure custody of packages, and completing delivery 
               with customer authentication. */
        
        subject scoutVehicle : AmazonScout;
        
        assume constraint packageAssigned {
            doc /* A valid package with destination address is assigned to Scout. */
        }
        
        assume constraint routeAccessible {
            doc /* Delivery route is accessible via sidewalks and designated paths. */
        }
        
        assume constraint weatherConditions {
            doc /* Weather conditions are within operational limits. */
        }
        
        require safetyReq : SafetyRequirement;
        require payloadReq : PayloadRequirement;
        require autonomyReq : AutonomyRequirement;
        require enduranceReq : EnduranceRequirement;
        
        require constraint successfulDelivery {
            doc /* Package must be delivered to correct address with customer confirmation. */
        }
        
        require constraint secureTransit {
            doc /* Package must remain locked and secure throughout transit. */
        }
    }
}

// --- Test harness (auto-generated) ---
package ExecutionHarness {
    private import ISQ::*;
    private import SI::*;
    private import ScalarValues::*;
    private import AmazonScoutDeliverySystem::*;
}

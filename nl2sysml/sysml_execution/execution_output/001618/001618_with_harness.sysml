package 'Utility Fog System' {
    private import ScalarValues::*;
    private import ISQ::*;
    private import SI::*;
    
    attribute def FogletIdentifier;
    attribute def Position3D {
        attribute x : LengthValue;
        attribute y : LengthValue;
        attribute z : LengthValue;
    }
    attribute def LinkStrength :> Real;
    attribute def ConfigurationPattern;
    attribute def MaterialDensity :> DensityValue;
    attribute def StructuralLoad :> ForceValue;
    
    attribute def LinkageForce :> ForceValue;
    attribute def ProcessingCapacity :> PowerValue;
    attribute def CommunicationBandwidth;
    attribute def ReconfigurationTime :> TimeValue;
    
    port def PowerPort {
        attribute voltage : ElectricPotentialValue;
        attribute current : ElectricCurrentValue;
    }
    
    port def CommunicationPort {
        attribute transmitBandwidth : CommunicationBandwidth;
        attribute receiveBandwidth : CommunicationBandwidth;
    }
    
    port def MechanicalLinkPort {
        attribute linkForce : LinkageForce;
        attribute extended : Boolean;
        attribute connected : Boolean;
    }
    
    part def Foglet {
        doc /* 
        A microscopic robotic unit capable of autonomous movement, 
        computation, and mechanical linkage with neighboring foglets.
        */
        
        attribute id : FogletIdentifier;
        attribute position : Position3D;
        attribute processingPower : ProcessingCapacity;
        attribute energyLevel : EnergyValue;
        
        port powerIn : PowerPort;
        port commPort : CommunicationPort[12];
        port mechanicalArm : MechanicalLinkPort[12];
        
        part processor {
            attribute computeCapacity : ProcessingCapacity;
            attribute memorySize : Real;
        }
        
        part actuator[12] {
            attribute extensionLength : LengthValue;
            attribute graspForce : LinkageForce;
            attribute maxExtension : LengthValue;
        }
        
        part sensor {
            attribute proximityRange : LengthValue;
            attribute detectedNeighbors : FogletIdentifier[*];
            attribute environmentalData : Real;
        }
        
        part communicationModule {
            attribute bandwidth : CommunicationBandwidth;
            attribute range : LengthValue;
            attribute protocol : String;
        }
        
        part powerManagement {
            attribute batteryCapacity : EnergyValue;
            attribute currentDraw : ElectricCurrentValue;
        }
    }
    
    part def FogletCluster {
        doc /* 
        A collection of interconnected foglets forming a cohesive structure.
        */
        
        part foglets : Foglet[*];
        attribute clusterSize : Integer;
        attribute currentConfiguration : ConfigurationPattern;
        attribute structuralIntegrity : LinkStrength;
        
        connection fogletLinks : MechanicalLink[*] 
            connect foglets.mechanicalArm to foglets.mechanicalArm;
        
        connection commNetwork : CommunicationLink[*]
            connect foglets.commPort to foglets.commPort;
    }
    
    connection def MechanicalLink {
        end fogletA : MechanicalLinkPort;
        end fogletB : MechanicalLinkPort;
        attribute linkStrength : LinkStrength;
        attribute bondType : String;
    }
    
    connection def CommunicationLink {
        end portA : CommunicationPort;
        end portB : CommunicationPort;
        attribute latency : TimeValue;
    }
    
    item def TargetObject {
        attribute shape : ConfigurationPattern;
        attribute requiredDensity : MaterialDensity;
        attribute dimensions : Position3D;
        attribute mechanicalProperties : StructuralLoad;
    }
    
    requirement def UtilityFogRequirements {
        doc /* 
        Top-level requirements for the utility fog system to dynamically 
        form arbitrary structures and objects on demand.
        */
        
        requirement reconfigurationSpeed {
            doc /* 
            The system shall reconfigure from one shape to another 
            within a specified maximum time.
            */
            attribute maxReconfigTime : ReconfigurationTime;
            require constraint { maxReconfigTime <= 10.0[SI::s] }
        }
        
        requirement structuralIntegrity {
            doc /* 
            The formed structure shall maintain specified load capacity 
            without failure or deformation.
            */
            attribute minLoadCapacity : StructuralLoad;
            require constraint { minLoadCapacity >= 1000.0[SI::N] }
        }
        
        requirement scalability {
            doc /* 
            The system shall operate effectively with variable numbers 
            of foglets from thousands to millions.
            */
            attribute minFoglets : Integer;
            attribute maxFoglets : Integer;
            require constraint { minFoglets >= 1000 }
            require constraint { maxFoglets <= 1000000 }
        }
        
        requirement energyEfficiency {
            doc /* 
            The system shall minimize energy consumption during 
            reconfiguration and maintenance operations.
            */
            attribute maxPowerConsumption : PowerValue;
            require constraint { maxPowerConsumption <= 100.0[SI::W] }
        }
    }
    
    action def SenseEnvironment {
        in fogletPosition : Position3D;
        in sensorRange : LengthValue;
        out nearbyFoglets : FogletIdentifier[*];
        out targetDetected : Boolean;
        out environmentalConditions : Real;
    }
    
    action def ComputeConfiguration {
        in targetShape : ConfigurationPattern;
        in availableFoglets : FogletIdentifier[*];
        in currentPositions : Position3D[*];
        out newPositions : Position3D[*];
        out linkageCommands : Boolean[*];
        out energyEstimate : EnergyValue;
    }
    
    action def ExtendArms {
        in targetPosition : Position3D;
        in armIndex : Integer;
        out extensionComplete : Boolean;
        out actualExtension : LengthValue;
    }
    
    action def FormLink {
        in neighborID : FogletIdentifier;
        in armIndex : Integer;
        out linkEstablished : Boolean;
        out linkStrength : LinkStrength;
    }
    
    action def ReleaseLink {
        in armIndex : Integer;
        out linkReleased : Boolean;
    }
    
    action def ReconfigureStructure {
        doc /* 
        Coordinate foglet movements and linkages to transform the swarm 
        from its current configuration to a target configuration.
        */
        
        in targetConfiguration : ConfigurationPattern;
        in cluster : FogletCluster;
        out reconfigurationSuccess : Boolean;
        out reconfigTime : ReconfigurationTime;
        
        first start;
        then action sense : SenseEnvironment {
            in fogletPosition;
            in sensorRange;
            out nearbyFoglets;
            out targetDetected;
            out environmentalConditions;
        }
        then action compute : ComputeConfiguration {
            in targetShape = targetConfiguration;
            in availableFoglets = sense.nearbyFoglets;
            in currentPositions;
            out newPositions;
            out linkageCommands;
            out energyEstimate;
        }
        then decide;
            if compute.linkageCommands->size() > 0 then executeReconfig;
            if compute.linkageCommands->size() == 0 then completeAction;
        
        action executeReconfig {
            first action releaseOldLinks : ReleaseLink[*] {
                in armIndex;
                out linkReleased;
            }
            then action moveToPosition : ExtendArms[*] {
                in targetPosition;
                in armIndex;
                out extensionComplete;
                out actualExtension;
            }
            then action formNewLinks : FormLink[*] {
                in neighborID;
                in armIndex;
                out linkEstablished;
                out linkStrength;
            }
        }
        then completeAction;
        
        action completeAction {
            assign reconfigurationSuccess := true;
        }
        then done;
    }
    
    action def MaintainStructure {
        doc /* 
        Continuously monitor and adjust linkages to maintain structural 
        integrity under external loads and environmental conditions.
        */
        
        in currentConfig : ConfigurationPattern;
        in externalLoad : StructuralLoad;
        out structureStable : Boolean;
        
        loop {
            action monitorLoads {
                in load : StructuralLoad = externalLoad;
                out loadDistribution : StructuralLoad[*];
                out stressPoints : Position3D[*];
            }
            then decide;
                if monitorLoads.loadDistribution->size() > 0 
                    then reinforceLinks;
                else continueMonitoring;
            
            action reinforceLinks {
                action adjustLinkStrength {
                    in targetStrength : LinkStrength;
                    out adjusted : Boolean;
                }
                action redistributeLoad {
                    in stressPoints : Position3D[*] = monitorLoads.stressPoints;
                    out redistributed : Boolean;
                }
            }
            then continueMonitoring;
            
            merge continueMonitoring;
        }
    }
    
    action def SelfHeal {
        doc /* 
        Detect and repair damaged or failed foglets by rerouting 
        connections and redistributing functionality.
        */
        
        in cluster : FogletCluster;
        out healingComplete : Boolean;
        
        first start;
        then action detectFailures {
            out failedFoglets : FogletIdentifier[*];
            out affectedRegions : Position3D[*];
        }
        then decide;
            if detectFailures.failedFoglets->size() > 0 then repair;
            else skipRepair;
        
        action repair {
            action isolateFailures {
                in failed : FogletIdentifier[*] = detectFailures.failedFoglets;
                out isolated : Boolean;
            }
            then action rerouteConnections {
                in affectedRegions : Position3D[*] = detectFailures.affectedRegions;
                out rerouted : Boolean;
            }
            then action verifyIntegrity {
                out verified : Boolean;
            }
        }
        then skipRepair;
        
        merge skipRepair;
        then assign healingComplete := true;
        then done;
    }
    
    part utilityFogSystem : FogletCluster {
        doc /* 
        A utility fog system composed of numerous microscopic robotic foglets 
        that can dynamically interconnect and reconfigure to form arbitrary 
        three-dimensional structures and objects on demand. The system provides 
        programmable matter capable of transforming into tools, furniture, 
        protective barriers, or any other physical form as needed.
        */
        
        attribute systemSize : Integer = 50000;
        attribute operationalMode : ConfigurationPattern;
        attribute totalEnergy : EnergyValue;
        attribute systemHealth : Real;
        
        part fogletArray : Foglet[50000];
        
        part centralController {
            attribute coordinationAlgorithm : String;
            attribute globalState : ConfigurationPattern;
        }
        
        perform action primaryFunction : ReconfigureStructure {
            in targetConfiguration = utilityFogSystem::operationalMode;
            in cluster = utilityFogSystem;
            out reconfigurationSuccess;
            out reconfigTime;
        }
        
        perform action structuralMaintenance : MaintainStructure {
            in currentConfig = utilityFogSystem::operationalMode;
            in externalLoad;
            out structureStable;
        }
        
        perform action autonomousHealing : SelfHeal {
            in cluster = utilityFogSystem;
            out healingComplete;
        }
    }
    
    action def UtilityFogOperation {
        doc /* 
        Primary high-level function: Transform a distributed swarm of microscopic 
        robotic foglets into any desired macroscopic object or structure by 
        coordinating individual foglet movements, linkages, and collective behavior. 
        The system enables programmable matter that can dynamically change form, 
        density, and mechanical properties to serve diverse functional needs.
        */
        
        in desiredObject : TargetObject;
        out formedStructure : ConfigurationPattern;
        out operationSuccess : Boolean;
        
        first start;
        then action initializeSwarm {
            action distributeControl {
                out controllerAssigned : Boolean;
            }
            action establishCommunication {
                out networkReady : Boolean;
            }
            action calibrateSensors {
                out sensorsCalibrated : Boolean;
            }
        }
        then action analyzeTarget {
            in targetSpec : TargetObject = desiredObject;
            out requiredFogletCount : Integer;
            out configurationPlan : ConfigurationPattern;
            out feasibilityAssessment : Boolean;
        }
        then decide;
            if analyzeTarget.feasibilityAssessment then proceedWithFormation;
            else abortOperation;
        
        action proceedWithFormation {
            action executeFormation : ReconfigureStructure {
                in targetConfiguration = analyzeTarget.configurationPlan;
                in cluster;
                out reconfigurationSuccess;
                out reconfigTime;
            }
            then action stabilizeStructure : MaintainStructure {
                in currentConfig = analyzeTarget.configurationPlan;
                in externalLoad;
                out structureStable;
            }
            then action verifyFormation {
                in targetSpec : TargetObject = desiredObject;
                in actualConfig : ConfigurationPattern = analyzeTarget.configurationPlan;
                out verified : Boolean;
            }
            then action finalizeStructure {
                assign formedStructure := analyzeTarget.configurationPlan;
                assign operationSuccess := verifyFormation.verified;
            }
        }
        then completeOp;
        
        action abortOperation {
            assign operationSuccess := false;
        }
        then completeOp;
        
        merge completeOp;
        then done;
    }
    
    requirement utilityFogSystemRequirements : UtilityFogRequirements {
        subject fogSystem : FogletCluster :> utilityFogSystem;
        
        assume constraint validFogletCount {
            fogSystem.clusterSize >= 1000
        }
        
        assume constraint sufficientEnergy {
            fogSystem.totalEnergy >= 1000.0[SI::J]
        }
        
        require reconfigurationSpeed {
            attribute maxReconfigTime = 8.0[SI::s];
        }
        
        require structuralIntegrity {
            attribute minLoadCapacity = 2000.0[SI::N];
        }
        
        require scalability {
            attribute minFoglets = 1000;
            attribute maxFoglets = 100000;
        }
        
        require energyEfficiency {
            attribute maxPowerConsumption = 75.0[SI::W];
        }
    }
}

// --- Test harness (auto-generated) ---
package ExecutionHarness {
    private import ScalarValues::*;
    private import ISQ::*;
    private import SI::*;
    private import 'Utility Fog System'::*;

    action orchestrator {
        attribute testTargetConfiguration : ConfigurationPattern;
        action executeFormationProbe : ReconfigureStructure {
            in targetConfiguration = testTargetConfiguration;
            // TODO(human): unsupported input type for cluster: FogletCluster (type is not a primitive, enum, extracted payload def, or known value type)
        }
        first executeFormationProbe;
    }
}

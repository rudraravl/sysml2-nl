package 'Energid Robotic Manipulation System' {
	private import ScalarValues::*;
	private import ISQ::*;
	private import SI::*;
	
	attribute def JointConfiguration {
		attribute positions : AngleValue[7];
		attribute velocities : AngularVelocityValue[7];
		attribute accelerations : AngularAccelerationValue[7];
	}
	
	attribute def CartesianPose {
		attribute position : LengthValue[3];
		attribute orientation : AngleValue[4];
	}
	
	attribute def WorkspaceObstacle {
		attribute center : LengthValue[3];
		attribute radius : LengthValue;
	}
	
	attribute def MotionPlan {
		attribute waypoints : JointConfiguration[*] ordered;
		attribute duration : TimeValue;
		attribute isValid : Boolean;
	}
	
	attribute def GraspParameters {
		attribute approachVector : Real[3];
		attribute graspForce : ForceValue;
		attribute fingerPositions : LengthValue[2];
	}
	
	attribute def TaskSpecification {
		attribute targetPose : CartesianPose;
		attribute graspParams : GraspParameters;
		attribute constraints : String[*];
	}
	
	attribute def SystemStatus {
		attribute operationalMode : OperationalMode;
		attribute errorCode : Integer;
		attribute timestamp : TimeValue;
	}
	
	enum def OperationalMode {
		idle;
		planning;
		executing;
		grasping;
		error;
	}
	
	requirement def CollisionAvoidanceRequirement {
		doc /* The system shall plan and execute all motions such that the manipulator 
		     maintains a minimum clearance of 50mm from all detected obstacles. */
		attribute minClearance : LengthValue = 50.0[SI::mm];
	}
	
	requirement def PositionAccuracyRequirement {
		doc /* The end effector shall reach target positions with accuracy within 2mm 
		     in translation and 0.5 degrees in orientation. */
		attribute maxTranslationError : LengthValue = 2.0[SI::mm];
		attribute maxOrientationError : AngleValue = 0.5[SI::deg];
	}
	
	requirement def PlanningTimeRequirement {
		doc /* Motion planning shall complete within 500ms for typical manipulation tasks. */
		attribute maxPlanningTime : TimeValue = 500.0[SI::ms];
	}
	
	requirement def SafetyRequirement {
		doc /* The system shall immediately halt all motion upon detection of unexpected 
		     contact forces exceeding 50N. */
		attribute maxContactForce : ForceValue = 50.0[SI::N];
	}
	
	requirement def AdaptiveControlRequirement {
		doc /* The system shall continuously update motion plans based on real-time 
		     sensor feedback to adapt to dynamic environments. */
	}
	
	port def SensorDataPort {
		out currentJointState : JointConfiguration;
		out detectedObstacles : WorkspaceObstacle[*];
		out contactForces : ForceValue[*];
	}
	
	port def ControlCommandPort {
		in targetJointState : JointConfiguration;
		in graspCommand : GraspParameters;
	}
	
	port def PlanningPort {
		in taskSpec : TaskSpecification;
		out motionPlan : MotionPlan;
		out planningStatus : SystemStatus;
	}
	
	port def ExecutionPort {
		in motionPlan : MotionPlan;
		out executionProgress : Real;
		out executionStatus : SystemStatus;
	}
	
	action def PerceiveEnvironment {
		out currentState : JointConfiguration;
		out obstacles : WorkspaceObstacle[*];
		out forces : ForceValue[*];
	}
	
	action def SolveInverseKinematics {
		in targetPose : CartesianPose;
		in currentConfig : JointConfiguration;
		in obstacles : WorkspaceObstacle[*];
		out solution : JointConfiguration;
		out isReachable : Boolean;
	}
	
	action def OptimizeMotionTrajectory {
		in rawPath : JointConfiguration[*];
		out optimizedPlan : MotionPlan;
	}
	
	action def ExecuteTrajectory {
		in plan : MotionPlan;
		in feedback : JointConfiguration;
		out commands : JointConfiguration;
		out progress : Real;
		
		private attribute currentWaypoint : Integer := 0;
		private attribute totalWaypoints : Integer;
		
		first start;
		then merge controlLoop;
		
		action readFeedback {
			in currentState = feedback;
		}
		then action computeControl {
			in desiredState = plan.waypoints->at(currentWaypoint);
			in actualState = readFeedback.currentState;
			out controlCommand = commands;
		}
		then action updateProgress {
			assign currentWaypoint := currentWaypoint + 1;
			assign progress := currentWaypoint / totalWaypoints;
		}
		then decide;
			if currentWaypoint < totalWaypoints then controlLoop;
			if currentWaypoint >= totalWaypoints then done;
	}
	
	action def PerformGrasp {
		in graspParams : GraspParameters;
		out graspSuccess : Boolean;
		
		first start;
		then action approach {
			in approachVector = graspParams.approachVector;
		}
		then action closeGripper {
			in targetForce = graspParams.graspForce;
			in fingerPos = graspParams.fingerPositions;
		}
		then action verifyGrasp {
			out success = graspSuccess;
		}
		then done;
	}
	
	action def MonitorSystemSafety {
		in forces : ForceValue[*];
		in obstacles : WorkspaceObstacle[*];
		out status : SystemStatus;
		out emergencyStop : Boolean;
		
		first start;
		then merge monitorLoop;
		
		action checkForces {
			in contactForces = forces;
			out forceViolation : Boolean;
		}
		then action checkCollisions {
			in detectedObstacles = obstacles;
			out collisionRisk : Boolean;
		}
		then decide;
			if checkForces.forceViolation or checkCollisions.collisionRisk then triggerStop;
			if not (checkForces.forceViolation or checkCollisions.collisionRisk) then monitorLoop;
		
		action triggerStop {
			assign emergencyStop := true;
		}
		then done;
	}
	
	action def PlanCollisionFreeMotion {
		in task : TaskSpecification;
		in currentState : JointConfiguration;
		in obstacles : WorkspaceObstacle[*];
		out plan : MotionPlan;
		
		first start;
		then action solveIK : SolveInverseKinematics {
			in targetPose = task.targetPose;
			in currentConfig = currentState;
			in obstacles = obstacles;
			out solution;
			out isReachable;
		}
		then decide;
			if solveIK.isReachable then generatePath;
			if not solveIK.isReachable then reportFailure;
		
		action generatePath {
			private attribute pathWaypoints : JointConfiguration[*];
		}
		then action optimizePath : OptimizeMotionTrajectory {
			in rawPath = generatePath.pathWaypoints;
			out optimizedPlan = plan;
		}
		then action validatePlan {
			in planToValidate = optimizePath.optimizedPlan;
			out validationResult : Boolean;
		}
		then decide;
			if validatePlan.validationResult then done;
			if not validatePlan.validationResult then generatePath;
		
		action reportFailure;
		then done;
	}
	
	part def PerceptionModule {
		doc /* Processes sensor data to build environmental model and track robot state. */
		out port sensorOutput : SensorDataPort;
		
		perform action perceiveEnvironment : PerceiveEnvironment;
	}
	
	part def MotionPlanningModule {
		doc /* Computes collision-free trajectories using Energid's advanced kinematics engine. */
		in port taskInput : PlanningPort;
		in port sensorInput : SensorDataPort;
		out port planOutput : PlanningPort;
		
		perform action planMotion : PlanCollisionFreeMotion;
	}
	
	part def KinematicsEngine {
		doc /* Energid's core inverse/forward kinematics solver with constraint handling. */
		attribute redundancyResolution : String = "optimization-based";
		
		perform action solveKinematics : SolveInverseKinematics;
	}
	
	part def TrajectoryOptimizer {
		doc /* Optimizes planned trajectories for smoothness and execution time. */
		perform action optimizeTrajectory : OptimizeMotionTrajectory;
	}
	
	part def MotionController {
		doc /* Executes planned trajectories with real-time feedback control. */
		in port planInput : ExecutionPort;
		in port feedbackInput : SensorDataPort;
		out port controlOutput : ControlCommandPort;
		
		perform action executeMotion : ExecuteTrajectory;
	}
	
	part def ManipulatorArm {
		doc /* 7-DOF robotic manipulator with integrated sensors. */
		in port commandInput : ControlCommandPort;
		out port stateOutput : SensorDataPort;
		
		attribute dof : Integer = 7;
		attribute maxReach : LengthValue = 850.0[SI::mm];
		attribute payload : MassValue = 5.0[SI::kg];
	}
	
	part def EndEffector {
		doc /* Adaptive gripper with force sensing. */
		in port graspInput : GraspParameters;
		out port forceOutput : ForceValue;
		
		perform action executeGrasp : PerformGrasp;
	}
	
	part def SafetyMonitor {
		doc /* Monitors system state and enforces safety constraints. */
		in port monitorInput : SensorDataPort;
		out port safetyStatus : SystemStatus;
		
		perform action monitorSafety : MonitorSystemSafety;
	}
	
	action def AutonomousManipulation {
		in task : TaskSpecification;
		out completionStatus : SystemStatus;
		
		first start;
		then action sense : PerceiveEnvironment {
			out currentState;
			out obstacles;
			out forces;
		}
		then action plan : PlanCollisionFreeMotion {
			in task = task;
			in currentState = sense.currentState;
			in obstacles = sense.obstacles;
			out plan;
		}
		then decide;
			if plan.plan.isValid then execute;
			if not plan.plan.isValid then replan;
		
		action execute : ExecuteTrajectory {
			in plan = plan.plan;
			in feedback = sense.currentState;
			out commands;
			out progress;
		}
		then action grasp : PerformGrasp {
			in graspParams = task.graspParams;
			out graspSuccess;
		}
		then decide;
			if grasp.graspSuccess then done;
			if not grasp.graspSuccess then replan;
		
		action replan;
		then plan;
	}
	
	part def EnergidManipulationSystem;
	
	part energidManipulationSystem : EnergidManipulationSystem {
		doc /* 
		Energid Technologies robotic manipulation system provides advanced motion planning,
		control, and execution capabilities for complex manipulation tasks. The system's 
		primary function is to autonomously plan and execute collision-free trajectories 
		that move a robotic manipulator from its current configuration to grasp and 
		manipulate objects in cluttered environments. It uses Energid's proprietary 
		kinematics engine to solve complex inverse kinematics problems with obstacle 
		avoidance, optimizes trajectories for smooth execution, and adapts in real-time 
		to dynamic environmental changes through continuous sensor feedback.
		*/
		
		attribute currentTask : TaskSpecification;
		attribute systemState : SystemStatus;
		
		part perception : PerceptionModule;
		part planner : MotionPlanningModule;
		part kinematics : KinematicsEngine;
		part optimizer : TrajectoryOptimizer;
		part controller : MotionController;
		part arm : ManipulatorArm;
		part gripper : EndEffector;
		part safety : SafetyMonitor;
		
		connection perceptionToPlanner : FlowConnection
			connect perception.sensorOutput to planner.sensorInput;
		
		connection perceptionToController : FlowConnection
			connect perception.sensorOutput to controller.feedbackInput;
		
		connection perceptionToSafety : FlowConnection
			connect perception.sensorOutput to safety.monitorInput;
		
		connection plannerToController : FlowConnection
			connect planner.planOutput to controller.planInput;
		
		connection controllerToArm : FlowConnection
			connect controller.controlOutput to arm.commandInput;
		
		connection armToPerception : FlowConnection
			connect arm.stateOutput to perception.sensorOutput;
		
		satisfy collisionAvoidance : CollisionAvoidanceRequirement;
		satisfy positionAccuracy : PositionAccuracyRequirement;
		satisfy planningTime : PlanningTimeRequirement;
		satisfy safety : SafetyRequirement;
		satisfy adaptiveControl : AdaptiveControlRequirement;
		
		perform action autonomousManipulation : AutonomousManipulation;
	}
}

// --- Test harness (auto-generated) ---
package ExecutionHarness {
    private import ScalarValues::*;
    private import ISQ::*;
    private import SI::*;
    private import 'Energid Robotic Manipulation System'::*;

    action orchestrator {
        action executeProbe : ExecuteTrajectory {
            // TODO(human): unsupported input type for plan: MotionPlan (unsupported structured payload members: waypoints)
            // TODO(human): unsupported input type for feedback: JointConfiguration (unsupported structured payload members: positions, velocities, accelerations)
        }
        first executeProbe;
    }
}

package 'Action Performance Example' {
	private import 'Action Decomposition'::*;
	
	part def Camera;
	part def AutoFocus;
	part def Imager;
	
	part camera : Camera {
		
		perform action takePhoto[*] ordered 
			references takePicture;
		
		part f : AutoFocus {
			perform takePhoto.focus;			
		}
		
		part i : Imager {
			perform takePhoto.shoot;
		}		
	}
}

// --- Test harness (auto-generated) ---
package ExecutionHarness {
    private import 'Action Decomposition'::*;
    private import 'Action Performance Example'::*;
    part testSubject : Camera;
}

package PhotodetectorSystem {
    private import ScalarValues::*;
    private import ISQ::*;
    private import SI::*;
    
    attribute def PhotonFluxValue :> Real {
        doc /* Rate of photons incident per unit area */
    }
    
    attribute def PhotocurrentValue :> ElectricCurrentValue {
        doc /* Current generated by photoelectric effect */
    }
    
    attribute def QuantumEfficiencyValue :> Real {
        doc /* Ratio of charge carriers generated to incident photons */
    }
    
    attribute def ResponsivityValue :> Real {
        doc /* Output current per unit incident optical power (A/W) */
    }
    
    attribute def WavelengthValue :> LengthValue {
        doc /* Wavelength of incident electromagnetic radiation */
    }
    
    attribute def BiasVoltageValue :> ElectricPotentialValue {
        doc /* Applied reverse bias voltage across photodetector junction */
    }
    
    attribute def DarkCurrentValue :> ElectricCurrentValue {
        doc /* Leakage current in absence of illumination */
    }
    
    item def OpticalSignal {
        attribute photonFlux : PhotonFluxValue;
        attribute wavelength : WavelengthValue;
        attribute power : PowerValue;
    }
    
    item def ElectricalSignal {
        attribute current : PhotocurrentValue;
        attribute voltage : ElectricPotentialValue;
    }
    
    port def OpticalPort {
        in attribute incidentLight : OpticalSignal;
    }
    
    port def ElectricalPort {
        out attribute outputSignal : ElectricalSignal;
    }
    
    port def BiasPort {
        in attribute biasVoltage : BiasVoltageValue;
    }
    
    part def PhotodetectorElement {
        doc /* Semiconductor junction that converts photons to electron-hole pairs */
        
        attribute quantumEfficiency : QuantumEfficiencyValue;
        attribute responsivity : ResponsivityValue;
        attribute darkCurrent : DarkCurrentValue;
        attribute activeArea : AreaValue;
        attribute spectralRange : WavelengthValue[2];
        
        port opticalInput : OpticalPort;
        port electricalOutput : ElectricalPort;
        port biasInput : BiasPort;
    }
    
    part def TransimpedanceAmplifier {
        doc /* Converts photocurrent to proportional voltage signal */
        
        attribute transimpedanceGain : Real;
        attribute bandwidth : FrequencyValue;
        attribute inputNoiseCurrent : ElectricCurrentValue;
        
        port currentInput {
            in attribute inputCurrent : PhotocurrentValue;
        }
        
        port voltageOutput {
            out attribute outputVoltage : ElectricPotentialValue;
        }
    }
    
    part def SignalConditioner {
        doc /* Filters and amplifies detector output for downstream processing */
        
        attribute voltageGain : Real;
        attribute lowPassCutoff : FrequencyValue;
        attribute highPassCutoff : FrequencyValue;
        
        port signalInput {
            in attribute inputVoltage : ElectricPotentialValue;
        }
        
        port signalOutput {
            out attribute conditionedVoltage : ElectricPotentialValue;
        }
    }
    
    part def BiasSupply {
        doc /* Provides stable reverse bias voltage to photodetector */
        
        attribute nominalVoltage : BiasVoltageValue;
        attribute currentLimit : ElectricCurrentValue;
        attribute voltageStability : Real;
        
        port biasOutput {
            out attribute outputVoltage : BiasVoltageValue;
        }
    }
    
    action def PhotonAbsorption {
        doc /* Photons absorbed in depletion region generate electron-hole pairs */
        
        in incidentFlux : PhotonFluxValue;
        in wavelength : WavelengthValue;
        in efficiency : QuantumEfficiencyValue;
        in area : AreaValue;
        out carrierPairs : Real;
    }
    
    action def CarrierSeparation {
        doc /* Electric field separates charge carriers creating photocurrent */
        
        in carrierPairs : Real;
        in biasVoltage : BiasVoltageValue;
        in responsivity : ResponsivityValue;
        out photocurrent : PhotocurrentValue;
    }
    
    action def CurrentToVoltageConversion {
        doc /* Transimpedance amplifier converts current to voltage */
        
        in inputCurrent : PhotocurrentValue;
        in gain : Real;
        out outputVoltage : ElectricPotentialValue;
    }
    
    action def SignalConditioning {
        doc /* Filter and amplify voltage signal */
        
        in rawVoltage : ElectricPotentialValue;
        in voltageGain : Real;
        in filterCutoff : FrequencyValue;
        out conditionedVoltage : ElectricPotentialValue;
    }
    
    action def DetectOpticalSignal {
        doc /* Complete photodetection process from photons to conditioned electrical signal */
        
        in opticalInput : OpticalSignal;
        in bias : BiasVoltageValue;
        in detectorQE : QuantumEfficiencyValue;
        in detectorResponsivity : ResponsivityValue;
        in detectorArea : AreaValue;
        in tiaGain : Real;
        in conditionerGain : Real;
        out finalSignal : ElectricalSignal;
        
        private attribute generatedCurrent : PhotocurrentValue;
        private attribute amplifiedVoltage : ElectricPotentialValue;
        private attribute processedVoltage : ElectricPotentialValue;
        
        first start;
        
        then action absorb : PhotonAbsorption {
            in incidentFlux = opticalInput.photonFlux;
            in wavelength = opticalInput.wavelength;
            in efficiency = detectorQE;
            in area = detectorArea;
            out carrierPairs;
        }
        
        then action separate : CarrierSeparation {
            in carrierPairs = absorb.carrierPairs;
            in biasVoltage = bias;
            in responsivity = detectorResponsivity;
            out photocurrent;
        }
        
        then assign generatedCurrent := separate.photocurrent;
        
        then action convert : CurrentToVoltageConversion {
            in inputCurrent = generatedCurrent;
            in gain = tiaGain;
            out outputVoltage;
        }
        
        then assign amplifiedVoltage := convert.outputVoltage;
        
        then action condition : SignalConditioning {
            in rawVoltage = amplifiedVoltage;
            in voltageGain = conditionerGain;
            in filterCutoff = 100000.0 [Hz];
            out conditionedVoltage;
        }
        
        then assign processedVoltage := condition.conditionedVoltage;
        
        then assign finalSignal := ElectricalSignal {
            :>> current = generatedCurrent;
            :>> voltage = processedVoltage;
        };
        
        then done;
    }
    
    state def PhotodetectorOperatingStates {
        doc /* Operating state machine for photodetector system */
        
        entry; then standby;
        
        state standby {
            doc /* System powered but no significant optical input */
        }
        
        transition standby_to_detecting
            first standby
            accept at when opticalPowerDetected
            then detecting;
        
        state detecting {
            doc /* Active photodetection and signal generation */
            
            entry action performDetection : DetectOpticalSignal;
        }
        
        transition detecting_to_amplifying
            first detecting
            accept at when photocurrentGenerated
            then amplifying;
        
        state amplifying {
            doc /* Transimpedance amplification active */
        }
        
        transition amplifying_to_conditioning
            first amplifying
            accept at when voltageSignalReady
            then conditioning;
        
        state conditioning {
            doc /* Signal filtering and final amplification */
        }
        
        transition conditioning_to_outputting
            first conditioning
            accept at when signalConditioned
            then outputting;
        
        state outputting {
            doc /* Providing conditioned electrical output signal */
        }
        
        transition outputting_to_standby
            first outputting
            accept at when opticalInputCeased
            then standby;
        
        transition detecting_to_saturated
            first detecting
            if opticalPowerExcessive
            then saturated;
        
        state saturated {
            doc /* Detector saturated due to excessive optical power */
        }
        
        transition saturated_to_standby
            first saturated
            accept at when opticalPowerReduced
            then standby;
    }
    
    requirement def QuantumEfficiencyRequirement {
        doc /* Photodetector shall maintain minimum quantum efficiency */
        
        subject detector : PhotodetectorElement;
        
        require constraint {
            detector.quantumEfficiency >= 0.65
        }
    }
    
    requirement def DarkCurrentRequirement {
        doc /* Dark current shall remain below specified maximum */
        
        subject detector : PhotodetectorElement;
        
        require constraint {
            detector.darkCurrent <= 1.0e-9 [A]
        }
    }
    
    requirement def BandwidthRequirement {
        doc /* System bandwidth shall support required signal frequencies */
        
        subject amplifier : TransimpedanceAmplifier;
        
        require constraint {
            amplifier.bandwidth >= 1.0e6 [Hz]
        }
    }
    
    requirement def SpectralRangeRequirement {
        doc /* Detector shall operate over specified wavelength range */
        
        subject detector : PhotodetectorElement;
        
        require constraint {
            detector.spectralRange[1] >= 400.0e-9 [m] and
            detector.spectralRange[2] <= 1100.0e-9 [m]
        }
    }
    
    requirement <'PDR-SYS-001'> photodetectionSystemRequirement {
        doc /* System shall convert incident optical radiation into proportional electrical signal */
        
        subject system : PhotodetectorSystem;
        
        assume constraint operatingConditions {
            doc /* System operates within specified environmental and optical conditions */
            system.ambientTemperature >= 253.15 [K] and
            system.ambientTemperature <= 323.15 [K]
        }
        
        require QuantumEfficiencyRequirement;
        require DarkCurrentRequirement;
        require BandwidthRequirement;
        require SpectralRangeRequirement;
    }
    
    part def PhotodetectorSystem {
        doc /* Complete photodetector system converting optical signals to electrical signals */
        
        attribute ambientTemperature : TemperatureValue;
        attribute operatingWavelength : WavelengthValue;
        attribute detectionSensitivity : PhotonFluxValue;
        
        part detector : PhotodetectorElement;
        part tia : TransimpedanceAmplifier;
        part conditioner : SignalConditioner;
        part biasSupply : BiasSupply;
    }
    
    part photodetectorSystem : PhotodetectorSystem {
        
        :>> ambientTemperature = 298.15 [K];
        :>> operatingWavelength = 850.0e-9 [m];
        
        part detector : PhotodetectorElement {
            :>> quantumEfficiency = 0.85;
            :>> responsivity = 0.65;
            :>> darkCurrent = 5.0e-10 [A];
            :>> activeArea = 1.0e-6 [m^2];
            :>> spectralRange = (400.0e-9 [m], 1100.0e-9 [m]);
        }
        
        part tia : TransimpedanceAmplifier {
            :>> transimpedanceGain = 1.0e6;
            :>> bandwidth = 2.0e6 [Hz];
            :>> inputNoiseCurrent = 1.0e-12 [A];
        }
        
        part conditioner : SignalConditioner {
            :>> voltageGain = 10.0;
            :>> lowPassCutoff = 1.0e5 [Hz];
            :>> highPassCutoff = 10.0 [Hz];
        }
        
        part biasSupply : BiasSupply {
            :>> nominalVoltage = 5.0 [V];
            :>> currentLimit = 0.1 [A];
            :>> voltageStability = 0.001;
        }
        
        connect biasSupply.biasOutput to detector.biasInput;
        connect detector.electricalOutput to tia.currentInput;
        connect tia.voltageOutput to conditioner.signalInput;
        
        perform action detectAndCondition : DetectOpticalSignal {
            in opticalInput;
            in bias = biasSupply.nominalVoltage;
            in detectorQE = detector.quantumEfficiency;
            in detectorResponsivity = detector.responsivity;
            in detectorArea = detector.activeArea;
            in tiaGain = tia.transimpedanceGain;
            in conditionerGain = conditioner.voltageGain;
            out finalSignal;
        }
        
        exhibit state operatingBehavior : PhotodetectorOperatingStates;
    }
}

// --- Test harness (auto-generated) ---
package ExecutionHarness {
    private import ScalarValues::*;
    private import ISQ::*;
    private import SI::*;
    private import PhotodetectorSystem::*;

    part photodetectorSystem : PhotodetectorElement {
        exhibit state sm : PhotodetectorOperatingStates;
    }

    action orchestrator {
        attribute testIncidentFlux : PhotonFluxValue = 0.0;
        attribute testWavelength : WavelengthValue;
        attribute testEfficiency : QuantumEfficiencyValue = 0.0;
        attribute testArea : AreaValue;
        action actionProbe : PhotonAbsorption {
            // TODO(human): unsupported input type for depletion: unknown (missing declared type)
            in incidentFlux = testIncidentFlux;
            in wavelength = testWavelength;
            in efficiency = testEfficiency;
            in area = testArea;
        }
        first actionProbe;
    }
}

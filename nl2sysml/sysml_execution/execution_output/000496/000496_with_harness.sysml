package ReviventTranscatheterSystem {
    private import ScalarValues::*;
    private import ISQ::*;
    private import SI::*;
    
    attribute def VentricularVolumeValue :> VolumeValue;
    attribute def EjectionFractionValue :> Real;
    attribute def AnchorTensionValue :> ForceValue;
    attribute def CatheterPositionValue :> LengthValue;
    
    enum def AnchorDeploymentState {
        retracted;
        deployed;
        secured;
        failed;
    }
    
    enum def ProcedurePhase {
        preparation;
        navigation;
        deployment;
        tensioning;
        procedureVerification;
        completion;
    }
    
    attribute def VentricularGeometry {
        attribute endDiastolicVolume : VentricularVolumeValue;
        attribute endSystolicVolume : VentricularVolumeValue;
        attribute ejectionFraction : EjectionFractionValue;
        attribute wallThickness : LengthValue;
    }
    
    attribute def AnchorConfiguration {
        attribute numberOfAnchors : Integer;
        attribute anchorSpacing : LengthValue;
        attribute tensionLevel : AnchorTensionValue;
        attribute deploymentStatus : AnchorDeploymentState;
    }
    
    item def BloodFlow;
    item def ContrastMedium;
    item def FluoroscopicImage;
    
    port def VascularAccessPort {
        in flow bloodIn : BloodFlow;
        out flow bloodOut : BloodFlow;
        in flow contrast : ContrastMedium;
    }
    
    port def ImagingPort {
        out flow imagingData : FluoroscopicImage;
    }
    
    port def AnchorControlPort {
        in tensionCommand : AnchorTensionValue;
        out tensionFeedback : AnchorTensionValue;
        out deploymentState : AnchorDeploymentState;
    }
    
    part def LeftVentricle {
        attribute geometry : VentricularGeometry;
        attribute scarTissueLocation : LengthValue[*];
        port vascularAccess : VascularAccessPort;
        port imaging : ImagingPort;
    }
    
    part def DeliveryCatheterSystem {
        attribute catheterPosition : CatheterPositionValue;
        attribute catheterDiameter : LengthValue;
        port vascularInterface : VascularAccessPort;
        port imagingInterface : ImagingPort;
        port anchorControl : AnchorControlPort[*];
        
        action navigateToTarget {
            in targetPosition : CatheterPositionValue;
            out positionAchieved : Boolean;
        }
    }
    
    part def MicroAnchorArray {
        attribute anchorCount : Integer;
        attribute configuration : AnchorConfiguration;
        port controlInterface : ~AnchorControlPort[*];
        
        action deployAnchor {
            in anchorIndex : Integer;
            in targetTension : AnchorTensionValue;
            out deploymentSuccess : Boolean;
            out finalTension : AnchorTensionValue;
        }
    }
    
    part def FluoroscopyGuidanceSystem {
        port imagingOutput : ImagingPort;
        
        action acquireImage {
            in catheterPosition : CatheterPositionValue;
            out imageData : FluoroscopicImage;
        }
        
        action verifyPlacement {
            in imageData : FluoroscopicImage;
            out placementCorrect : Boolean;
        }
    }
    
    part def TensioningMechanism {
        attribute currentTension : AnchorTensionValue;
        attribute targetTension : AnchorTensionValue;
        
        action adjustTension {
            in desiredTension : AnchorTensionValue;
            out achievedTension : AnchorTensionValue;
        }
        
        action lockTension {
            out tensionLocked : Boolean;
        }
    }
    
    action def NavigateCatheter {
        in targetLocation : CatheterPositionValue;
        in guidanceImages : FluoroscopicImage;
        out navigationComplete : Boolean;
    }
    
    action def DeployAnchorPair {
        in pairIndex : Integer;
        in targetTension : AnchorTensionValue;
        out firstAnchorDeployed : Boolean;
        out secondAnchorDeployed : Boolean;
        out pairSecured : Boolean;
    }
    
    action def ApplyTension {
        in anchorPairs : Integer;
        in tensionTarget : AnchorTensionValue;
        out ventricularRemodeled : Boolean;
    }
    
    action def VerifyRemodeling {
        in preGeometry : VentricularGeometry;
        in postGeometry : VentricularGeometry;
        out remodelingSuccessful : Boolean;
        out volumeReduction : VentricularVolumeValue;
    }
    
    state def ReviventProcedureStates {
        entry; then preparationState;
        
        state preparationState;
        
        transition preparationState_to_navigation
            first preparationState
            then navigationState;
        
        state navigationState {
            do action navigating : NavigateCatheter;
        }
        
        transition navigationState_to_deployment
            first navigationState
            then deploymentState;
        
        state deploymentState {
            do action deploying : DeployAnchorPair;
        }
        
        transition deploymentState_to_tensioning
            first deploymentState
            then tensioningState;
        
        transition deploymentState_to_navigation
            first deploymentState
            then navigationState;
        
        state tensioningState {
            do action tensioning : ApplyTension;
        }
        
        transition tensioningState_to_verificationState
            first tensioningState
            then verificationState;
        
        state verificationState {
            do action verifying : VerifyRemodeling;
        }
        
        transition verificationState_to_completion
            first verificationState
            then completionState;
        
        transition verificationState_to_tensioning
            first verificationState
            then tensioningState;
        
        state completionState;
    }
    
    part def ReviventTranscatheterSystem {
        doc /*
            The Revivent Transcatheter Ventricular Enhancement System is a minimally invasive 
            cardiac device designed to treat heart failure by reshaping the left ventricle. 
            The system excludes non-functional scarred myocardial tissue through percutaneous 
            delivery of micro-anchors that plicate the ventricular wall, reducing chamber volume 
            and improving ejection fraction without requiring open-heart surgery.
        */
        
        attribute procedurePhase : ProcedurePhase;
        
        part catheterSystem : DeliveryCatheterSystem {
            attribute :>> catheterDiameter = 14[mm];
        }
        
        part anchorArray : MicroAnchorArray {
            attribute :>> anchorCount = 12;
        }
        
        part guidanceSystem : FluoroscopyGuidanceSystem;
        
        part tensioningSystem : TensioningMechanism {
            attribute :>> targetTension = 15[N];
        }
        
        part targetVentricle : LeftVentricle;
        
        connection catheterToVentricle 
            connect catheterSystem.vascularInterface to targetVentricle.vascularAccess;
        
        connection catheterToGuidance
            connect catheterSystem.imagingInterface to guidanceSystem.imagingOutput;
        
        connection catheterToAnchors
            connect catheterSystem.anchorControl to anchorArray.controlInterface;
        
        perform action performVentricularEnhancement {
            doc /*
                Primary therapeutic function: Percutaneously deliver and deploy micro-anchors 
                to exclude scarred myocardial tissue, reduce left ventricular volume, and 
                improve cardiac function through geometric remodeling.
            */
            
            in baselineGeometry : VentricularGeometry;
            in anchorPairCount : Integer;
            out finalGeometry : VentricularGeometry;
            out procedureSuccess : Boolean;
            
            first start;
            
            then action prepareAccess {
                out accessEstablished : Boolean;
            }
            
            then action navigateToScarRegion : NavigateCatheter {
                in targetLocation : CatheterPositionValue;
                out navigationComplete : Boolean;
            }
            
            then merge deploymentLoop;
            
            action deploymentLoop;
            
            private attribute deployedPairs : Integer := 0;
            
            for pairNumber in 1..anchorPairCount {
                perform action deployPair : DeployAnchorPair {
                    in pairIndex = pairNumber;
                    in targetTension = tensioningSystem.targetTension;
                    out firstAnchorDeployed : Boolean;
                    out secondAnchorDeployed : Boolean;
                    out pairSecured : Boolean;
                }
                
                then decide;
                    if deployPair.pairSecured then incrementCounter;
                    if not deployPair.pairSecured then repositionCatheter;
                
                action incrementCounter {
                    assign deployedPairs := deployedPairs + 1;
                }
                then deploymentLoop;
                
                action repositionCatheter : NavigateCatheter {
                    in targetLocation : CatheterPositionValue;
                    out navigationComplete : Boolean;
                }
                then deploymentLoop;
            }
            
            then action applyFinalTension : ApplyTension {
                in anchorPairs = deployedPairs;
                in tensionTarget = tensioningSystem.targetTension;
                out ventricularRemodeled : Boolean;
            }
            
            then action lockAnchors {
                out anchorsLocked : Boolean;
            }
            
            then action assessOutcome : VerifyRemodeling {
                in preGeometry = baselineGeometry;
                in postGeometry : VentricularGeometry;
                out remodelingSuccessful : Boolean;
                out volumeReduction : VentricularVolumeValue;
            }
            
            then action withdrawCatheter {
                out catheterRemoved : Boolean;
            }
            
            then assign finalGeometry := assessOutcome.postGeometry;
            then assign procedureSuccess := assessOutcome.remodelingSuccessful;
            then done;
        }
        
        exhibit state procedureBehavior : ReviventProcedureStates;
    }
    
    requirement def TherapeuticRequirement;
    requirement def SafetyRequirement;
    requirement def PerformanceRequirement;
    requirement def UsabilityRequirement;
    
    requirement <'REQ-RVT-001'> volumeReductionRequirement : TherapeuticRequirement {
        doc /*
            The Revivent system shall reduce left ventricular end-systolic volume 
            by at least 15% compared to baseline measurements.
        */
        
        subject reviventSystem : ReviventTranscatheterSystem;
        
        require constraint {
            reviventSystem.performVentricularEnhancement.finalGeometry.endSystolicVolume <= 
            reviventSystem.performVentricularEnhancement.baselineGeometry.endSystolicVolume * 0.85
        }
    }
    
    requirement <'REQ-RVT-002'> ejectionFractionImprovement : PerformanceRequirement {
        doc /*
            The Revivent system shall improve left ventricular ejection fraction 
            by a relative increase of at least 15% from baseline.
        */
        
        subject reviventSystem : ReviventTranscatheterSystem;
        
        require constraint {
            reviventSystem.performVentricularEnhancement.finalGeometry.ejectionFraction >= 
            reviventSystem.performVentricularEnhancement.baselineGeometry.ejectionFraction * 1.15
        }
    }
    
    requirement <'REQ-RVT-003'> anchorSecurityRequirement : SafetyRequirement {
        doc /*
            All deployed micro-anchors shall achieve and maintain secure fixation 
            with tension levels between 10N and 20N to prevent migration or tissue damage.
        */
        
        subject anchorArray : MicroAnchorArray;
        
        require constraint {
            anchorArray.configuration.tensionLevel >= 10[N] and
            anchorArray.configuration.tensionLevel <= 20[N] and
            anchorArray.configuration.deploymentStatus == AnchorDeploymentState::secured
        }
    }
    
    requirement <'REQ-RVT-004'> percutaneousDeliveryRequirement : UsabilityRequirement {
        doc /*
            The Revivent system shall be deliverable through a percutaneous femoral 
            approach using a catheter with maximum diameter of 14 millimeters.
        */
        
        subject catheterSystem : DeliveryCatheterSystem;
        
        require constraint {
            catheterSystem.catheterDiameter <= 14[mm]
        }
    }
    
    requirement <'REQ-RVT-005'> imagingGuidanceRequirement : SafetyRequirement {
        doc /*
            The Revivent system shall utilize continuous fluoroscopic guidance 
            during navigation and deployment to ensure accurate anchor placement.
        */
        
        subject guidanceSystem : FluoroscopyGuidanceSystem;
    }
    
    requirement reviventSystemMission {
        doc /*
            The Revivent Transcatheter Ventricular Enhancement System shall provide 
            minimally invasive treatment for heart failure patients by percutaneously 
            delivering micro-anchors to exclude scarred myocardial tissue, thereby 
            reducing left ventricular volume and improving cardiac function without 
            requiring open-heart surgery.
        */
        
        require volumeReductionRequirement;
        require ejectionFractionImprovement;
        require anchorSecurityRequirement;
        require percutaneousDeliveryRequirement;
        require imagingGuidanceRequirement;
    }
    
    part reviventSystem : ReviventTranscatheterSystem {
        satisfy reviventSystemMission;
    }
}

// --- Test harness (auto-generated) ---
package ExecutionHarness {
    private import ScalarValues::*;
    private import ISQ::*;
    private import SI::*;
    private import ReviventTranscatheterSystem::*;

    part testSubject : ReviventTranscatheterSystem {
    :>> targetLocation = testTargetLocation;
    }

    part testSubject : ReviventTranscatheterSystem {
        exhibit state procedureBehavior : ReviventProcedureStates;
    }

    action orchestrator {
        attribute testTargetLocation : CatheterPositionValue;
    }
}

package NanotechnologyDrugDeliverySystem {
    private import ScalarValues::*;
    private import ISQ::*;
    private import SI::*;
    
    attribute def NanometerValue :> LengthValue {
        doc /* Length measurement in nanometer scale (1-1000 nm) */
    }
    
    attribute def ConcentrationValue :> Real;
    attribute def AffinityValue :> Real;
    attribute def pHValue :> Real;
    
    item def ChemotherapeuticDrug {
        attribute molecularWeight :> MassValue;
        attribute therapeuticDose :> MassValue;
        attribute toxicityIndex :> Real;
    }
    
    item def CancerCellMarker {
        attribute proteinSignature : String;
        attribute expressionLevel :> ConcentrationValue;
    }
    
    item def HealthyTissue {
        attribute cellType : String;
    }
    
    attribute def PayloadCapacity :> MassValue;
    attribute def BindingStrength :> AffinityValue;
    attribute def ReleaseRate :> Real;
    
    port def ChemicalSensingPort {
        in markerConcentration : ConcentrationValue;
        in environmentalPH : pHValue;
        out detectionSignal : Boolean;
    }
    
    port def DrugStoragePort {
        in drugLoad : ChemotherapeuticDrug;
        out drugRelease : ChemotherapeuticDrug;
        attribute currentPayload :> PayloadCapacity;
    }
    
    port def NavigationPort {
        in bloodFlowVelocity : SpeedValue;
        in targetLocation : LengthValue[3];
        out currentPosition : LengthValue[3];
    }
    
    port def BindingPort {
        in targetMarker : CancerCellMarker;
        out bindingStatus : Boolean;
        attribute bindingStrength :> BindingStrength;
    }
    
    part def LipidBilayerShell {
        attribute thickness :> NanometerValue;
        attribute permeability :> Real;
        port structuralIntegrity;
    }
    
    part def PolymerCore {
        attribute diameter :> NanometerValue;
        attribute drugCapacity :> PayloadCapacity;
        port drugEncapsulation;
    }
    
    part def TargetingAntibody {
        attribute specificity :> AffinityValue;
        attribute bindingConstant :> Real;
        port antigenRecognition;
    }
    
    part def pHResponsiveGate {
        attribute activationPH :> pHValue;
        attribute releaseThreshold :> pHValue;
        port environmentSensor;
        port releaseControl;
    }
    
    action def LoadDrugPayload {
        in therapeuticAgent : ChemotherapeuticDrug;
        in maxCapacity : PayloadCapacity;
        out loadedAmount : PayloadCapacity;
        out loadingEfficiency : Real;
    }
    
    action def CirculateThroughBloodstream {
        in flowVelocity : SpeedValue;
        in currentPos : LengthValue[3];
        in targetPos : LengthValue[3];
        out newPosition : LengthValue[3];
        out distanceToTarget : LengthValue;
    }
    
    action def DetectCancerCell {
        in markerConcentration : ConcentrationValue;
        in antibodySpecificity : AffinityValue;
        out isCancerCell : Boolean;
        out confidenceLevel : Real;
    }
    
    action def BindToTargetCell {
        in targetMarker : CancerCellMarker;
        in antibodyAffinity : AffinityValue;
        out bindingAchieved : Boolean;
        out attachmentStrength : BindingStrength;
    }
    
    action def SenseLocalEnvironment {
        in localPH : pHValue;
        in localTemperature : TemperatureValue;
        out tumorEnvironmentDetected : Boolean;
        out releaseConditionMet : Boolean;
    }
    
    action def ReleaseDrugPayload {
        in storedPayload : PayloadCapacity;
        in releaseSignal : Boolean;
        in releaseRate : ReleaseRate;
        out releasedDose : MassValue;
        out remainingPayload : PayloadCapacity;
        out releaseComplete : Boolean;
    }
    
    action def MonitorSystemStatus {
        in payloadLevel : PayloadCapacity;
        in bindingStatus : Boolean;
        in position : LengthValue[3];
        out telemetryData : String;
    }
    
    state def NanocarrierOperationalStates {
        entry; then initialization;
        
        state initialization {
            entry action loadPayload : LoadDrugPayload;
        }
        transition init_to_circulation
            first initialization
            if loadPayload.loadingEfficiency > 0.8
            then circulation;
        
        state circulation {
            do action navigate : CirculateThroughBloodstream;
            do action scan : DetectCancerCell;
        }
        transition circulation_to_targeting
            first circulation
            if scan.isCancerCell and scan.confidenceLevel > 0.9
            then targeting;
        
        state targeting {
            entry action approach : CirculateThroughBloodstream;
            do action detect : DetectCancerCell;
        }
        transition targeting_to_binding
            first targeting
            if approach.distanceToTarget < 100.0
            then binding;
        
        state binding {
            entry action attach : BindToTargetCell;
            do action monitor : SenseLocalEnvironment;
        }
        transition binding_to_releasing
            first binding
            if attach.bindingAchieved and monitor.releaseConditionMet
            then releasing;
        
        state releasing {
            entry action deliverDrug : ReleaseDrugPayload;
            do action checkStatus : MonitorSystemStatus;
        }
        transition releasing_to_depleted
            first releasing
            if deliverDrug.releaseComplete
            then depleted;
        
        state depleted {
            do action finalStatus : MonitorSystemStatus;
        }
        then done;
    }
    
    action def AutonomousDrugDeliveryMission {
        in drug : ChemotherapeuticDrug;
        in targetMarkers : CancerCellMarker[*];
        in injectionSite : LengthValue[3];
        in tumorSite : LengthValue[3];
        out deliverySuccess : Boolean;
        out dosageDelivered : MassValue;
        
        first start;
        then action load : LoadDrugPayload {
            in therapeuticAgent = drug;
            in maxCapacity;
            out loadedAmount;
            out loadingEfficiency;
        }
        then merge navigationCycle;
        then action circulate : CirculateThroughBloodstream {
            in flowVelocity;
            in currentPos;
            in targetPos = tumorSite;
            out newPosition;
            out distanceToTarget;
        }
        then action detect : DetectCancerCell {
            in markerConcentration;
            in antibodySpecificity;
            out isCancerCell;
            out confidenceLevel;
        }
        then decide targetDecision;
            if detect.isCancerCell and detect.confidenceLevel > 0.9 then proceedToBinding;
            if not detect.isCancerCell or detect.confidenceLevel <= 0.9 then navigationCycle;
        action proceedToBinding;
        then action bind : BindToTargetCell {
            in targetMarker;
            in antibodyAffinity;
            out bindingAchieved;
            out attachmentStrength;
        }
        then action sense : SenseLocalEnvironment {
            in localPH;
            in localTemperature;
            out tumorEnvironmentDetected;
            out releaseConditionMet;
        }
        then decide releaseDecision;
            if sense.releaseConditionMet and bind.bindingAchieved then initiateRelease;
            if not sense.releaseConditionMet then waitForConditions;
        action waitForConditions;
        then sense;
        action initiateRelease;
        then action release : ReleaseDrugPayload {
            in storedPayload = load.loadedAmount;
            in releaseSignal = sense.releaseConditionMet;
            in releaseRate;
            out releasedDose;
            out remainingPayload;
            out releaseComplete;
        }
        then assign deliverySuccess := release.releaseComplete;
        then assign dosageDelivered := release.releasedDose;
        then done;
    }
    
    part def SmartNanocarrier {
        doc /*
            A smart nanocarrier is an engineered nanoscale drug delivery vehicle 
            designed to autonomously navigate the bloodstream, recognize cancer cells 
            through specific molecular markers, bind to tumor tissue, and release 
            therapeutic agents in response to the acidic tumor microenvironment.
            
            Primary Function: Targeted delivery of chemotherapeutic drugs to cancer 
            cells while minimizing exposure to healthy tissue, thereby reducing 
            systemic toxicity and improving treatment efficacy.
        */
        
        attribute carrierSize :> NanometerValue;
        attribute maxDrugLoad :> PayloadCapacity;
        attribute surfaceCharge :> Real;
        attribute circulationHalfLife :> TimeValue;
        
        part shell : LipidBilayerShell {
            attribute thickness = 5.0;
        }
        
        part core : PolymerCore {
            attribute diameter = carrierSize;
            attribute drugCapacity = maxDrugLoad;
        }
        
        part antibodies : TargetingAntibody[20..100] {
            attribute specificity;
        }
        
        part releaseGate : pHResponsiveGate {
            attribute activationPH = 6.5;
            attribute releaseThreshold = 6.0;
        }
        
        port sensingPort : ChemicalSensingPort;
        port storagePort : DrugStoragePort;
        port navigationPort : NavigationPort;
        port bindingPort : BindingPort;
        
        connect shell.structuralIntegrity to core.drugEncapsulation;
        connect core.drugEncapsulation to storagePort;
        connect antibodies.antigenRecognition to bindingPort;
        connect releaseGate.environmentSensor to sensingPort;
        connect releaseGate.releaseControl to storagePort;
        
        perform action deliveryMission : AutonomousDrugDeliveryMission[*];
        
        exhibit state operationalState : NanocarrierOperationalStates {
            perform deliveryMission.load during initialization;
            perform deliveryMission.circulate during circulation;
            perform deliveryMission.detect during circulation;
            perform deliveryMission.bind during binding;
            perform deliveryMission.sense during binding;
            perform deliveryMission.release during releasing;
        }
    }
    
    part def NanocarrierSwarm {
        part carriers : SmartNanocarrier[10000..100000];
        attribute totalDrugPayload :> MassValue;
        attribute swarmDensity :> ConcentrationValue;
        attribute deploymentVolume :> VolumeValue;
    }
    
    requirement def BiocompatibilityRequirement {
        doc /* Biocompatibility and safety requirements for nanomedicine */
        subject carrier : SmartNanocarrier;
        
        require constraint materialSafety {
            doc /* All nanocarrier materials must be biocompatible and biodegradable */
        }
        
        require constraint sizeConstraint {
            doc /* Carrier size must be 50-200 nm for optimal circulation and tumor penetration */
            carrier.carrierSize >= 50.0 and carrier.carrierSize <= 200.0
        }
        
        require constraint circulationTime {
            doc /* Circulation half-life must be 6-24 hours for effective tumor accumulation */
            carrier.circulationHalfLife >= 21600.0 and carrier.circulationHalfLife <= 86400.0
        }
    }
    
    requirement def TargetingEfficiencyRequirement {
        doc /* Requirements for selective targeting and drug delivery */
        subject carrier : SmartNanocarrier;
        
        require constraint selectivity {
            doc /* Targeting antibodies must achieve >95% specificity for cancer cell markers */
        }
        
        require constraint bindingAffinity {
            doc /* Antibody-antigen binding affinity must be >10^8 M^-1 */
        }
        
        require constraint tumorAccumulation {
            doc /* At least 5% of injected dose must accumulate in tumor tissue */
        }
    }
    
    requirement def DrugReleaseRequirement {
        doc /* Requirements for controlled drug release */
        subject carrier : SmartNanocarrier;
        
        require constraint pHSensitivity {
            doc /* Drug release must be triggered at pH 6.0-6.5 (tumor microenvironment) */
        }
        
        require constraint releaseKinetics {
            doc /* 80% of payload must be released within 24 hours of tumor binding */
        }
        
        require constraint payloadProtection {
            doc /* Drug payload must remain >90% stable during circulation */
        }
    }
    
    requirement <'NANO-SYS-001'> smartNanocarrierSystemRequirement {
        doc /*
            The smart nanocarrier system shall deliver chemotherapeutic drugs 
            specifically to cancer cells with high selectivity, controlled release 
            in the tumor microenvironment, and minimal systemic toxicity.
        */
        
        subject system : SmartNanocarrier;
        
        assume constraint physiologicalConditions {
            doc /* System operates in human bloodstream at 37°C, pH 7.4, with normal blood flow */
        }
        
        assume constraint tumorCharacteristics {
            doc /* Target tumors express specific surface markers and have acidic microenvironment (pH 6.0-6.8) */
        }
        
        require biocompatibility : BiocompatibilityRequirement {
            subject carrier = system;
        }
        
        require targeting : TargetingEfficiencyRequirement {
            subject carrier = system;
        }
        
        require release : DrugReleaseRequirement {
            subject carrier = system;
        }
        
        require constraint autonomousOperation {
            doc /* System must operate autonomously after intravenous injection without external control */
        }
        
        require constraint therapeuticEfficacy {
            doc /* System must achieve >50% reduction in tumor volume compared to conventional chemotherapy */
        }
    }
    
    part cancerTherapySystem : NanocarrierSwarm {
        doc /*
            Primary Function: Autonomous Targeted Cancer Therapy
            
            This nanotechnology-based system delivers chemotherapeutic drugs directly 
            to cancer cells through intelligent nanocarriers that circulate in the 
            bloodstream, recognize tumor-specific molecular markers, bind selectively 
            to cancer cells, and release their therapeutic payload in response to the 
            acidic tumor microenvironment. This targeted approach maximizes drug 
            concentration at tumor sites while minimizing systemic exposure and 
            toxicity to healthy tissues, representing a paradigm shift from 
            conventional systemic chemotherapy to precision nanomedicine.
        */
        
        attribute totalDrugPayload = 100.0;
        attribute swarmDensity = 1.0e12;
        attribute deploymentVolume = 50.0;
        
        satisfy smartNanocarrierSystemRequirement;
    }
}

// --- Test harness (auto-generated) ---
package ExecutionHarness {
    private import ScalarValues::*;
    private import ISQ::*;
    private import SI::*;
    private import NanotechnologyDrugDeliverySystem::*;

    part testSubject : SmartNanocarrier {
        exhibit state operationalState : NanocarrierOperationalStates;
    }

    action orchestrator {
        attribute testMaxCapacity : PayloadCapacity;
        action actionProbe : LoadDrugPayload {
            // TODO(human): unsupported input type for therapeuticAgent: ChemotherapeuticDrug (unsupported structured payload members: toxicityIndex)
            in maxCapacity = testMaxCapacity;
        }
        first actionProbe;
    }
}

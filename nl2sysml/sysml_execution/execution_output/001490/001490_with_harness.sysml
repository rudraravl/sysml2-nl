package LonWorksDistributedControlSystem {
    private import ScalarValues::*;
    private import ISQ::*;
    private import SI::*;
    private import Time::*;
    
    attribute def NeuronID :> String;
    attribute def DomainID :> Integer;
    attribute def SubnetID :> Integer;
    attribute def NodeID :> Integer;
    
    attribute def DataRateValue :> Real;
    attribute def LatencyValue :> Real;
    attribute def TemperatureSetpointValue :> Real;
    attribute def HumidityValue :> Real;
    attribute def AirflowValue :> Real;
    
    enum def MessagePriority {
        normal;
        urgent;
        critical;
    }
    
    enum def NodeStatus {
        unconfigured;
        configured;
        online;
        offline;
        error;
    }
    
    item def LonTalkMessage {
        attribute sourceNeuronID : NeuronID;
        attribute destinationNeuronID : NeuronID;
        attribute priority : MessagePriority;
        attribute payload : Real;
        attribute timestamp : Real;
    }
    
    item def NetworkVariable {
        attribute variableID : String;
        attribute value : Real;
        attribute lastUpdate : Real;
    }
    
    port def LonTalkPort {
        attribute neuronID : NeuronID;
        out item txMessages : LonTalkMessage[*];
        in item rxMessages : LonTalkMessage[*];
    }
    
    part def LonWorksNode {
        attribute neuronID : NeuronID;
        attribute domainID : DomainID;
        attribute subnetID : SubnetID;
        attribute nodeID : NodeID;
        attribute status : NodeStatus;
        
        port lonPort : LonTalkPort {
            attribute :>> neuronID = neuronID;
        }
        
        part neuronChip {
            attribute firmwareVersion : String;
            attribute processingPower : Real;
        }
        
        part transceiver {
            attribute dataRate : DataRateValue;
            attribute transmitPower : Real;
        }
    }
    
    part def TemperatureSensorNode :> LonWorksNode {
        attribute measuredTemperature : TemperatureSetpointValue;
        attribute sensorAccuracy : Real;
        attribute samplingInterval : Real;
        
        part temperatureSensor {
            attribute range : Real;
            attribute resolution : Real;
        }
        
        action def MeasureTemperature {
            out temperature : TemperatureSetpointValue;
        }
        
        action def TransmitReading {
            in reading : TemperatureSetpointValue;
            out message : LonTalkMessage;
        }
    }
    
    part def HumiditySensorNode :> LonWorksNode {
        attribute measuredHumidity : HumidityValue;
        attribute sensorAccuracy : HumidityValue;
        attribute samplingInterval : Real;
        
        part humiditySensor {
            attribute range : HumidityValue;
            attribute resolution : HumidityValue;
        }
        
        action def MeasureHumidity {
            out humidity : HumidityValue;
        }
        
        action def TransmitReading {
            in reading : HumidityValue;
            out message : LonTalkMessage;
        }
    }
    
    part def HVACControllerNode :> LonWorksNode {
        attribute temperatureSetpoint : TemperatureSetpointValue;
        attribute humiditySetpoint : HumidityValue;
        attribute currentTemperature : TemperatureSetpointValue;
        attribute currentHumidity : HumidityValue;
        attribute coolingOutput : Real;
        attribute heatingOutput : Real;
        attribute ventilationOutput : AirflowValue;
        
        part controlAlgorithm {
            attribute proportionalGain : Real;
            attribute integralGain : Real;
            attribute derivativeGain : Real;
        }
        
        action def ProcessSensorData {
            in tempReading : TemperatureSetpointValue;
            in humidReading : HumidityValue;
            out controlDecision : Real;
        }
        
        action def ComputeControlSignal {
            in setpoint : TemperatureSetpointValue;
            in measured : TemperatureSetpointValue;
            out controlSignal : Real;
        }
        
        action def TransmitCommand {
            in command : Real;
            out message : LonTalkMessage;
        }
        
        action def ControlLoop {
            first start;
            then merge continueControl;
            
            then action receiveSensorData {
                out tempData : TemperatureSetpointValue;
                out humidData : HumidityValue;
            }
            
            then action processData : ProcessSensorData {
                in tempReading = receiveSensorData.tempData;
                in humidReading = receiveSensorData.humidData;
            }
            
            then action computeControl : ComputeControlSignal {
                in setpoint = temperatureSetpoint;
                in measured = receiveSensorData.tempData;
            }
            
            then action sendCommand : TransmitCommand {
                in command = computeControl.controlSignal;
            }
            
            then decide;
                if sendCommand.message.priority == MessagePriority::critical then handleCritical;
                if sendCommand.message.priority != MessagePriority::critical then continueControl;
            
            action handleCritical {
                out criticalHandled : Boolean;
            }
            then continueControl;
        }
    }
    
    part def DamperActuatorNode :> LonWorksNode {
        attribute damperPosition : Real;
        attribute targetPosition : Real;
        attribute actuationSpeed : Real;
        
        part damperMotor {
            attribute maxTorque : Real;
            attribute responseTime : Real;
        }
        
        action def ReceiveCommand {
            in message : LonTalkMessage;
            out position : Real;
        }
        
        action def ActuateDamper {
            in targetPos : Real;
            out actualPos : Real;
        }
        
        action def ReportStatus {
            in currentPos : Real;
            out statusMessage : LonTalkMessage;
        }
    }
    
    part def FanActuatorNode :> LonWorksNode {
        attribute fanSpeed : Real;
        attribute targetSpeed : Real;
        attribute airflow : AirflowValue;
        
        part fanMotor {
            attribute maxSpeed : Real;
            attribute power : Real;
        }
        
        action def ReceiveCommand {
            in message : LonTalkMessage;
            out speed : Real;
        }
        
        action def ControlFan {
            in targetSpd : Real;
            out actualSpd : Real;
        }
        
        action def ReportStatus {
            in currentSpeed : Real;
            out statusMessage : LonTalkMessage;
        }
    }
    
    part def LonWorksNetwork {
        attribute networkDataRate : DataRateValue;
        attribute maxLatency : LatencyValue;
        attribute topology : String;
        
        part physicalLayer {
            attribute mediumType : String;
            attribute maxSegmentLength : Real;
            attribute maxNodes : Integer;
        }
        
        part dataLinkLayer {
            attribute protocolVersion : String;
            attribute collisionDetection : Boolean;
        }
    }
    
    requirement def PrimarySystemFunction {
        doc /* 
         * The LonWorks distributed control system shall provide automated
         * environmental control by continuously monitoring temperature and
         * humidity conditions through distributed sensor nodes, processing
         * this data in intelligent controller nodes using control algorithms,
         * and commanding actuator nodes to adjust HVAC equipment (dampers and fans)
         * to maintain desired environmental setpoints throughout the controlled space.
         * All communication between nodes shall utilize the LonTalk protocol
         * over the LonWorks network infrastructure.
         */
        subject system : LonWorksDistributedControlSystem;
    }
    
    requirement def NetworkPerformance {
        doc /* 
         * The LonWorks network shall support a minimum data rate of 78 kbps
         * and maintain end-to-end message latency below 100 milliseconds
         * for critical control messages.
         */
        subject network : LonWorksNetwork;
        
        assert constraint dataRateRequirement {
            network.networkDataRate >= 78.0
        }
        
        assert constraint latencyRequirement {
            network.maxLatency <= 100.0
        }
    }
    
    requirement def ControlAccuracy {
        doc /* 
         * The HVAC controller shall maintain temperature within +/- 1 degree Celsius
         * of the setpoint under normal operating conditions.
         */
        subject controller : HVACControllerNode;
    }
    
    requirement def SensorReliability {
        doc /* 
         * Temperature and humidity sensors shall provide readings with
         * specified accuracy and update at regular intervals.
         */
        subject tempSensor : TemperatureSensorNode;
        subject humidSensor : HumiditySensorNode;
    }
    
    requirement def ActuatorResponse {
        doc /* 
         * Actuator nodes shall respond to control commands within 500 milliseconds
         * and report status back to the controller.
         */
        subject damper : DamperActuatorNode;
        subject fan : FanActuatorNode;
    }
    
    part buildingAutomationSystem {
        doc /* 
         * A complete LonWorks-based building automation system for HVAC control
         * in a commercial facility. The system uses distributed intelligence
         * across multiple nodes connected via a LonWorks network to monitor
         * and control environmental conditions.
         */
        
        part network : LonWorksNetwork {
            attribute :>> networkDataRate = 78.0;
            attribute :>> maxLatency = 95.0;
            attribute :>> topology = "free topology";
            
            part :>> physicalLayer {
                attribute :>> mediumType = "twisted pair";
                attribute :>> maxSegmentLength = 500.0;
                attribute :>> maxNodes = 64;
            }
            
            part :>> dataLinkLayer {
                attribute :>> protocolVersion = "LonTalk 1.5";
                attribute :>> collisionDetection = true;
            }
        }
        
        part zoneTempSensor : TemperatureSensorNode {
            attribute :>> neuronID = "TEMP_SENSOR_001";
            attribute :>> domainID = 1;
            attribute :>> subnetID = 1;
            attribute :>> nodeID = 10;
            attribute :>> status = NodeStatus::online;
            attribute :>> measuredTemperature = 295.0;
            attribute :>> sensorAccuracy = 0.5;
            attribute :>> samplingInterval = 5.0;
            
            part :>> temperatureSensor {
                attribute :>> range = 50.0;
                attribute :>> resolution = 0.1;
            }
            
            part :>> transceiver {
                attribute :>> dataRate = 78.0;
                attribute :>> transmitPower = 10.0;
            }
        }
        
        part zoneHumiditySensor : HumiditySensorNode {
            attribute :>> neuronID = "HUMID_SENSOR_001";
            attribute :>> domainID = 1;
            attribute :>> subnetID = 1;
            attribute :>> nodeID = 11;
            attribute :>> status = NodeStatus::online;
            attribute :>> measuredHumidity = 45.0;
            attribute :>> sensorAccuracy = 2.0;
            attribute :>> samplingInterval = 5.0;
            
            part :>> humiditySensor {
                attribute :>> range = 100.0;
                attribute :>> resolution = 1.0;
            }
            
            part :>> transceiver {
                attribute :>> dataRate = 78.0;
                attribute :>> transmitPower = 10.0;
            }
        }
        
        part hvacController : HVACControllerNode {
            attribute :>> neuronID = "HVAC_CTRL_001";
            attribute :>> domainID = 1;
            attribute :>> subnetID = 1;
            attribute :>> nodeID = 20;
            attribute :>> status = NodeStatus::online;
            attribute :>> temperatureSetpoint = 295.0;
            attribute :>> humiditySetpoint = 50.0;
            attribute :>> currentTemperature = 295.0;
            attribute :>> currentHumidity = 45.0;
            attribute :>> coolingOutput = 0.0;
            attribute :>> heatingOutput = 0.0;
            attribute :>> ventilationOutput = 500.0;
            
            part :>> controlAlgorithm {
                attribute :>> proportionalGain = 1.2;
                attribute :>> integralGain = 0.5;
                attribute :>> derivativeGain = 0.1;
            }
            
            part :>> transceiver {
                attribute :>> dataRate = 78.0;
                attribute :>> transmitPower = 10.0;
            }
            
            perform action control[*] ordered references ControlLoop;
        }
        
        part airDamper : DamperActuatorNode {
            attribute :>> neuronID = "DAMPER_ACT_001";
            attribute :>> domainID = 1;
            attribute :>> subnetID = 1;
            attribute :>> nodeID = 30;
            attribute :>> status = NodeStatus::online;
            attribute :>> damperPosition = 50.0;
            attribute :>> targetPosition = 50.0;
            attribute :>> actuationSpeed = 10.0;
            
            part :>> damperMotor {
                attribute :>> maxTorque = 5.0;
                attribute :>> responseTime = 200.0;
            }
            
            part :>> transceiver {
                attribute :>> dataRate = 78.0;
                attribute :>> transmitPower = 10.0;
            }
        }
        
        part ventilationFan : FanActuatorNode {
            attribute :>> neuronID = "FAN_ACT_001";
            attribute :>> domainID = 1;
            attribute :>> subnetID = 1;
            attribute :>> nodeID = 31;
            attribute :>> status = NodeStatus::online;
            attribute :>> fanSpeed = 1200.0;
            attribute :>> targetSpeed = 1200.0;
            attribute :>> airflow = 500.0;
            
            part :>> fanMotor {
                attribute :>> maxSpeed = 3000.0;
                attribute :>> power = 250.0;
            }
            
            part :>> transceiver {
                attribute :>> dataRate = 78.0;
                attribute :>> transmitPower = 10.0;
            }
        }
        
        connection sensorToController1 : LonTalkMessage connect
            zoneTempSensor.lonPort.txMessages to
            hvacController.lonPort.rxMessages;
        
        connection sensorToController2 : LonTalkMessage connect
            zoneHumiditySensor.lonPort.txMessages to
            hvacController.lonPort.rxMessages;
        
        connection controllerToDamper : LonTalkMessage connect
            hvacController.lonPort.txMessages to
            airDamper.lonPort.rxMessages;
        
        connection controllerToFan : LonTalkMessage connect
            hvacController.lonPort.txMessages to
            ventilationFan.lonPort.rxMessages;
        
        connection damperToController : LonTalkMessage connect
            airDamper.lonPort.txMessages to
            hvacController.lonPort.rxMessages;
        
        connection fanToController : LonTalkMessage connect
            ventilationFan.lonPort.txMessages to
            hvacController.lonPort.rxMessages;
    }
    
    satisfy PrimarySystemFunction by buildingAutomationSystem;
    satisfy NetworkPerformance by buildingAutomationSystem.network;
    satisfy ControlAccuracy by buildingAutomationSystem.hvacController;
    satisfy SensorReliability by buildingAutomationSystem.zoneTempSensor;
    satisfy SensorReliability by buildingAutomationSystem.zoneHumiditySensor;
    satisfy ActuatorResponse by buildingAutomationSystem.airDamper;
    satisfy ActuatorResponse by buildingAutomationSystem.ventilationFan;
}

// --- Test harness (auto-generated) ---
package ExecutionHarness {
    private import ScalarValues::*;
    private import ISQ::*;
    private import SI::*;
    private import Time::*;
    private import LonWorksDistributedControlSystem::*;
}

package 'Cyborg System' {
	private import ScalarValues::*;
	private import ISQ::*;
	private import SI::*;
	
	attribute def NeuralSignal;
	attribute def MotorCommand;
	attribute def SensoryFeedback;
	attribute def CognitiveState;
	
	item def BloodOxygenLevel :> Real;
	item def NeuralVoltage :> ISQ::ElectricPotentialValue;
	item def ProcessorUtilization :> Real;
	item def BatteryCapacity :> ISQ::EnergyValue;
	
	port def NeuralInterfacePort {
		in item neuralInput : NeuralSignal;
		out item motorOutput : MotorCommand;
	}
	
	port def SensoryPort {
		out item visualData : SensoryFeedback;
		out item auditoryData : SensoryFeedback;
		out item tactileData : SensoryFeedback;
	}
	
	port def PowerPort {
		in item powerSupply : ISQ::PowerValue;
		out item powerDemand : ISQ::PowerValue;
	}
	
	part def BiologicalCore {
		attribute heartRate : ISQ::FrequencyValue;
		attribute oxygenSaturation : BloodOxygenLevel;
		attribute neuralActivity : NeuralVoltage;
		
		port neuralOutput : NeuralInterfacePort;
		port bioelectricPower : PowerPort;
		
		perform action generateNeuralIntent {
			out intentSignal : NeuralSignal;
		}
		
		perform action regulateHomeostasis {
			in oxygenLevel : BloodOxygenLevel;
			out metabolicPower : ISQ::PowerValue;
		}
	}
	
	part def CyberneticCore {
		attribute cpuLoad : ProcessorUtilization;
		attribute batteryLevel : BatteryCapacity;
		attribute operatingTemp : ISQ::ThermodynamicTemperatureValue;
		
		port neuralInput : NeuralInterfacePort;
		port sensoryOutput : SensoryPort;
		port powerManagement : PowerPort;
		
		part neuralDecoder {
			perform action decodeNeuralSignal {
				in rawSignal : NeuralSignal;
				out interpretedIntent : MotorCommand;
			}
		}
		
		part sensoryProcessor {
			perform action processSensoryData {
				out visualOutput : SensoryFeedback;
				out auditoryOutput : SensoryFeedback;
				out tactileOutput : SensoryFeedback;
			}
		}
		
		part powerController {
			perform action distributePower {
				in bioelectricInput : ISQ::PowerValue;
				in batteryInput : ISQ::PowerValue;
				out totalPower : ISQ::PowerValue;
			}
		}
	}
	
	part def CognitiveProcessor {
		attribute memoryStorage : Real;
		attribute computeSpeed : ISQ::FrequencyValue;
		
		perform action augmentCognition {
			in biologicalThought : NeuralSignal;
			in environmentalData : SensoryFeedback;
			out enhancedDecision : CognitiveState;
		}
	}
	
	part def BionicLimb {
		attribute jointAngle : Real;
		attribute actuatorForce : ISQ::ForceValue;
		attribute limbMass : ISQ::MassValue;
		
		port motorInterface : NeuralInterfacePort;
		port tactileSensor : SensoryPort;
		port limbPower : PowerPort;
		
		perform action executeMotion {
			in motorCmd : MotorCommand;
			out limbVelocity : ISQ::SpeedValue;
			out tactileFeedback : SensoryFeedback;
		}
	}
	
	action def IntegrateBioCybernetic {
		in biologicalIntent : NeuralSignal;
		in sensoryInput : SensoryFeedback;
		out motorControl : MotorCommand;
		out cognitiveOutput : CognitiveState;
		
		first start;
		then action decode {
			in rawIntent = biologicalIntent;
			out decodedCommand : MotorCommand;
		}
		then action fuse {
			in sensorData = sensoryInput;
			in command = decode.decodedCommand;
			out fusedOutput : CognitiveState;
		}
		then assign motorControl := decode.decodedCommand;
		then assign cognitiveOutput := fuse.fusedOutput;
		then done;
	}
	
	action def MonitorVitalSigns {
		in heartRate : ISQ::FrequencyValue;
		in oxygenLevel : BloodOxygenLevel;
		in temperature : ISQ::ThermodynamicTemperatureValue;
		out healthStatus : Real;
		
		first start;
		then decide;
			if heartRate >= 60.0 [SI::Hz] and heartRate <= 100.0 [SI::Hz] and
			   oxygenLevel >= 0.95 and temperature <= 310.0 [SI::K] 
			then normalStatus;
			else alertStatus;
		action normalStatus {
			assign healthStatus := 1.0;
		}
		then done;
		action alertStatus {
			assign healthStatus := 0.5;
		}
		then done;
	}
	
	action def AdaptToConditions {
		in environmentData : SensoryFeedback;
		in currentCognition : CognitiveState;
		out adaptiveResponse : MotorCommand;
		
		first start;
		then action analyzeEnvironment {
			in envData = environmentData;
			out analysisResult : CognitiveState;
		}
		then action generateResponse {
			in cogState = analyzeEnvironment.analysisResult;
			out responseCmd : MotorCommand;
		}
		then assign adaptiveResponse := generateResponse.responseCmd;
		then done;
	}
	
	state def CyborgOperationalMode {
		entry; then initialization;
		
		state initialization {
			entry assign mode := 'initializing';
		}
		then activeMode;
		
		state activeMode;
		accept when lowPower then powerSaveMode;
		accept when criticalError then safeMode;
		accept when optimalPerformance then enhancedMode;
		
		state powerSaveMode {
			entry assign mode := 'power saving';
		}
		accept when powerRestored then activeMode;
		
		state enhancedMode {
			entry assign mode := 'enhanced';
		}
		accept when lowPower then activeMode;
		
		state safeMode {
			entry assign mode := 'safe';
		}
		then decide;
			if errorCleared then activeMode;
			if fatalError then shutdownMode;
		
		state shutdownMode {
			entry assign mode := 'shutdown';
		}
		then done;
		
		attribute mode : String;
		attribute lowPower : Boolean;
		attribute powerRestored : Boolean;
		attribute criticalError : Boolean;
		attribute errorCleared : Boolean;
		attribute fatalError : Boolean;
		attribute optimalPerformance : Boolean;
	}
	
	requirement def CyborgSystemRequirements {
		doc /* The cyborg system shall integrate biological and cybernetic subsystems to augment human capabilities. */
		
		requirement <'REQ-001'> biologicalCompatibility {
			doc /* The system shall maintain biological homeostasis during all operational modes. */
			subject cyborg : Cyborg;
			assume constraint {
				cyborg.biologicalCore.oxygenSaturation >= 0.90
			}
			require constraint {
				cyborg.biologicalCore.heartRate >= 50.0 [SI::Hz] and
				cyborg.biologicalCore.heartRate <= 120.0 [SI::Hz]
			}
		}
		
		requirement <'REQ-002'> neuralResponseTime {
			doc /* Neural interface shall decode and execute commands within 100 milliseconds. */
			subject cyborg : Cyborg;
			require constraint {
				cyborg.cognitiveProcessor.computeSpeed >= 10.0 [SI::Hz]
			}
		}
		
		requirement <'REQ-003'> powerEndurance {
			doc /* The system shall operate continuously for at least 12 hours on internal power. */
			subject cyborg : Cyborg;
			require constraint {
				cyborg.cyberneticCore.batteryLevel >= 43200.0 [SI::kJ]
			}
		}
		
		requirement <'REQ-004'> limbStrength {
			doc /* Bionic limbs shall provide force output exceeding natural human limits by factor of 3. */
			subject limb : BionicLimb;
			require constraint {
				limb.actuatorForce >= 2400.0 [SI::N]
			}
		}
	}
	
	part cyborg : Cyborg {
		part biologicalCore : BiologicalCore {
			perform action generateNeuralIntent;
			perform action regulateHomeostasis;
		}
		
		part cyberneticCore : CyberneticCore {
			part neuralDecoder {
				perform action decodeNeuralSignal;
			}
			part sensoryProcessor {
				perform action processSensoryData;
			}
			part powerController {
				perform action distributePower;
			}
		}
		
		part cognitiveProcessor : CognitiveProcessor {
			perform action augmentCognition;
		}
		
		part leftArm : BionicLimb {
			perform action executeMotion;
		}
		
		part rightArm : BionicLimb {
			perform action executeMotion;
		}
		
		part leftLeg : BionicLimb {
			perform action executeMotion;
		}
		
		part rightLeg : BionicLimb {
			perform action executeMotion;
		}
		
		connection neuralLink connect 
			biologicalCore.neuralOutput to cyberneticCore.neuralInput;
		
		connection powerLink connect 
			biologicalCore.bioelectricPower to cyberneticCore.powerManagement;
		
		connection sensoryToLeftArm connect 
			cyberneticCore.sensoryOutput to leftArm.tactileSensor;
		
		connection sensoryToRightArm connect 
			cyberneticCore.sensoryOutput to rightArm.tactileSensor;
		
		connection motorToLeftArm connect 
			cyberneticCore.neuralInput to leftArm.motorInterface;
		
		connection motorToRightArm connect 
			cyberneticCore.neuralInput to rightArm.motorInterface;
		
		connection motorToLeftLeg connect 
			cyberneticCore.neuralInput to leftLeg.motorInterface;
		
		connection motorToRightLeg connect 
			cyberneticCore.neuralInput to rightLeg.motorInterface;
		
		perform action operateCyborg : IntegrateBioCybernetic {
			first start;
			then merge operationLoop;
			
			then action monitor : MonitorVitalSigns {
				in heartRate = biologicalCore.heartRate;
				in oxygenLevel = biologicalCore.oxygenSaturation;
				in temperature = cyberneticCore.operatingTemp;
				out healthStatus : Real;
			}
			
			then decide;
				if monitor.healthStatus >= 0.8 then normalOperation;
				if monitor.healthStatus < 0.8 then adaptiveOperation;
			
			action normalOperation {
				action processIntent {
					in biologicalIntent = biologicalCore.generateNeuralIntent.intentSignal;
					out motorControl : MotorCommand;
				}
				flow processIntent.motorControl to executeLeftArm.motorCmd;
				flow processIntent.motorControl to executeRightArm.motorCmd;
				
				action captureSensory {
					out sensoryInput : SensoryFeedback;
				}
				flow captureSensory.sensoryInput to enhanceCognition.environmentalData;
				
				action enhanceCognition : CognitiveProcessor::augmentCognition {
					in biologicalThought = biologicalCore.generateNeuralIntent.intentSignal;
					in environmentalData : SensoryFeedback;
					out enhancedDecision : CognitiveState;
				}
				
				action executeLeftArm : BionicLimb::executeMotion {
					in motorCmd : MotorCommand;
					out limbVelocity : ISQ::SpeedValue;
					out tactileFeedback : SensoryFeedback;
				}
				
				action executeRightArm : BionicLimb::executeMotion {
					in motorCmd : MotorCommand;
					out limbVelocity : ISQ::SpeedValue;
					out tactileFeedback : SensoryFeedback;
				}
			}
			then operationLoop;
			
			action adaptiveOperation : AdaptToConditions {
				in environmentData = cyberneticCore.sensoryProcessor.processSensoryData.visualOutput;
				in currentCognition = cognitiveProcessor.augmentCognition.enhancedDecision;
				out adaptiveResponse : MotorCommand;
			}
			then operationLoop;
			
			then done;
		}
		
		exhibit state operationalMode : CyborgOperationalMode;
		
		satisfy CyborgSystemRequirements::biologicalCompatibility;
		satisfy CyborgSystemRequirements::neuralResponseTime;
		satisfy CyborgSystemRequirements::powerEndurance;
	}
	
	action def CyborgPrimaryFunction {
		doc /* 
		The cyborg system's primary function is to seamlessly integrate biological and 
		cybernetic components to augment human physical and cognitive capabilities beyond 
		natural limits. The system continuously monitors biological vital signs, decodes 
		neural intent from the biological brain, processes environmental sensory data 
		through enhanced cybernetic sensors, and executes precise motor commands through 
		high-strength bionic limbs. Cognitive augmentation combines biological intuition 
		with computational processing to enable superior decision-making. The system 
		maintains biological homeostasis while delivering enhanced strength, endurance, 
		sensory perception, and cognitive performance, adapting dynamically to environmental 
		conditions and user intent through integrated bio-cybernetic feedback loops.
		*/
		
		in userIntent : NeuralSignal;
		in environmentalContext : SensoryFeedback;
		out enhancedCapability : CognitiveState;
		out physicalAction : MotorCommand;
	}
}

// --- Test harness (auto-generated) ---
package ExecutionHarness {
    private import ScalarValues::*;
    private import ISQ::*;
    private import SI::*;
    private import 'Cyborg System'::*;

    part cyborg : BiologicalCore {
        exhibit state sm : CyborgOperationalMode;
    }

    action orchestrator {
        attribute testEnvironmentalData : SensoryFeedback;
        action enhanceCognitionProbe : CognitiveProcessor {
            // TODO(human): unsupported input type for biologicalThought: unknown (missing declared type)
            in environmentalData = testEnvironmentalData;
        }
        first enhanceCognitionProbe;
    }
}

package 'Ethics of Technology System' {
	private import ScalarValues::*;
	private import ISQ::*;
	private import SI::*;
	
	attribute def RiskLevel;
	attribute def ComplianceScore;
	attribute def BiasMetric;
	attribute def PrivacyLevel;
	
	enum EthicalDecisionKind {
		approve;
		reject;
		escalate;
		requireReview;
	}
	
	enum ViolationSeverity {
		low;
		medium;
		high;
		critical;
	}
	
	item def TechnologyProposal {
		attribute proposalId : String;
		attribute technologyType : String;
		attribute intendedUse : String;
		attribute affectedPopulation : Integer;
		attribute dataCollectionScope : String;
		attribute automationLevel : Real;
	}
	
	item def EthicalAssessment {
		attribute assessmentId : String;
		attribute biasScore : BiasMetric;
		attribute privacyScore : PrivacyLevel;
		attribute transparencyScore : Real;
		attribute accountabilityScore : Real;
		attribute fairnessScore : Real;
		attribute overallRisk : RiskLevel;
		attribute complianceLevel : ComplianceScore;
		attribute timestamp : String;
	}
	
	item def EthicalDecision {
		attribute decisionId : String;
		attribute outcome : EthicalDecisionKind;
		attribute rationale : String;
		attribute conditions : String[*];
		attribute reviewerId : String;
		attribute requiresMonitoring : Boolean;
	}
	
	item def ViolationReport {
		attribute reportId : String;
		attribute violationType : String;
		attribute severity : ViolationSeverity;
		attribute affectedUsers : Integer;
		attribute detectionTime : String;
		attribute mitigationRequired : Boolean;
	}
	
	item def MonitoringData {
		attribute systemId : String;
		attribute usageMetrics : Real[*];
		attribute outcomeDistribution : Real[*];
		attribute userFeedback : String[*];
		attribute anomalyDetected : Boolean;
	}
	
	port def ProposalInputPort {
		in item proposal : TechnologyProposal;
	}
	
	port def AssessmentOutputPort {
		out item assessment : EthicalAssessment;
	}
	
	port def DecisionOutputPort {
		out item decision : EthicalDecision;
	}
	
	port def ViolationAlertPort {
		out item violation : ViolationReport;
	}
	
	port def MonitoringInputPort {
		in item monitoringData : MonitoringData;
	}
	
	part def BiasAnalysisEngine {
		attribute sensitiveAttributes : String[*];
		attribute biasThreshold : Real;
		attribute algorithmicFairnessEnabled : Boolean;
		
		port assessmentInput : ProposalInputPort;
		port biasOutput : AssessmentOutputPort;
		
		perform action analyzeBias {
			in proposal : TechnologyProposal;
			out biasMetric : BiasMetric;
			out fairnessScore : Real;
			out biasDetected : Boolean;
		}
	}
	
	part def PrivacyImpactAnalyzer {
		attribute dataMinimizationRequired : Boolean;
		attribute encryptionStandard : String;
		attribute consentMechanismRequired : Boolean;
		attribute retentionPolicyDefined : Boolean;
		
		port assessmentInput : ProposalInputPort;
		port privacyOutput : AssessmentOutputPort;
		
		perform action assessPrivacy {
			in proposal : TechnologyProposal;
			out privacyLevel : PrivacyLevel;
			out privacyRisks : String[*];
			out complianceStatus : Boolean;
		}
	}
	
	part def TransparencyEvaluator {
		attribute explainabilityRequired : Boolean;
		attribute auditTrailMandatory : Boolean;
		attribute userNotificationRequired : Boolean;
		
		port assessmentInput : ProposalInputPort;
		port transparencyOutput : AssessmentOutputPort;
		
		perform action evaluateTransparency {
			in proposal : TechnologyProposal;
			out transparencyScore : Real;
			out explainabilityLevel : String;
			out auditCapability : Boolean;
		}
	}
	
	part def AccountabilityFramework {
		attribute responsibilityAssigned : Boolean;
		attribute oversightMechanismDefined : Boolean;
		attribute remedyProcessEstablished : Boolean;
		
		port assessmentInput : ProposalInputPort;
		port accountabilityOutput : AssessmentOutputPort;
		
		perform action assessAccountability {
			in proposal : TechnologyProposal;
			out accountabilityScore : Real;
			out oversightLevel : String;
			out responsibilityChain : String[*];
		}
	}
	
	part def EthicalDecisionEngine {
		attribute approvalThreshold : Real;
		attribute escalationThreshold : Real;
		attribute humanReviewRequired : Boolean;
		
		port assessmentInput : AssessmentOutputPort;
		port decisionOutput : DecisionOutputPort;
		
		perform action makeEthicalDecision {
			in assessment : EthicalAssessment;
			out decision : EthicalDecision;
			out requiresEscalation : Boolean;
		}
	}
	
	part def ContinuousMonitoringSystem {
		attribute monitoringInterval : ISQ::TimeValue;
		attribute anomalyDetectionEnabled : Boolean;
		attribute feedbackLoopActive : Boolean;
		
		port monitoringInput : MonitoringInputPort;
		port violationOutput : ViolationAlertPort;
		
		perform action monitorDeployedSystem {
			in monitoringData : MonitoringData;
			out violationDetected : Boolean;
			out violationReport : ViolationReport;
		}
	}
	
	part def HumanOversightInterface {
		attribute reviewerCredentials : String[*];
		attribute escalationProtocol : String;
		attribute interventionAuthority : Boolean;
		
		perform action conductHumanReview {
			in assessment : EthicalAssessment;
			in initialDecision : EthicalDecision;
			out finalDecision : EthicalDecision;
			out additionalConditions : String[*];
		}
	}
	
	part def ComplianceValidator {
		attribute regulatoryFrameworks : String[*];
		attribute industryStandards : String[*];
		attribute legalRequirements : String[*];
		
		perform action validateCompliance {
			in proposal : TechnologyProposal;
			in assessment : EthicalAssessment;
			out complianceScore : ComplianceScore;
			out violations : String[*];
		}
	}
	
	part def EthicalGovernanceSystem {
		ref part biasEngine : BiasAnalysisEngine;
		ref part privacyAnalyzer : PrivacyImpactAnalyzer;
		ref part transparencyEval : TransparencyEvaluator;
		ref part accountabilityFramework : AccountabilityFramework;
		ref part decisionEngine : EthicalDecisionEngine;
		ref part monitoringSystem : ContinuousMonitoringSystem;
		ref part humanOversight : HumanOversightInterface;
		ref part complianceValidator : ComplianceValidator;
		
		attribute systemStatus : String;
		attribute activeProposals : Integer;
		attribute approvalRate : Real;
		attribute averageReviewTime : ISQ::TimeValue;
	}
	
	part ethicalGovernanceSystem : EthicalGovernanceSystem {
		part biasEngine : BiasAnalysisEngine;
		part privacyAnalyzer : PrivacyImpactAnalyzer;
		part transparencyEval : TransparencyEvaluator;
		part accountabilityFramework : AccountabilityFramework;
		part decisionEngine : EthicalDecisionEngine;
		part monitoringSystem : ContinuousMonitoringSystem;
		part humanOversight : HumanOversightInterface;
		part complianceValidator : ComplianceValidator;
		
		connection biasToDecision connect 
			biasEngine.biasOutput to decisionEngine.assessmentInput;
		connection privacyToDecision connect 
			privacyAnalyzer.privacyOutput to decisionEngine.assessmentInput;
		connection transparencyToDecision connect 
			transparencyEval.transparencyOutput to decisionEngine.assessmentInput;
		connection accountabilityToDecision connect 
			accountabilityFramework.accountabilityOutput to decisionEngine.assessmentInput;
		
		perform action evaluateTechnologyProposal[*] ordered 
			references ethicalEvaluationProcess;
	}
	
	action def ReceiveProposal {
		in proposal : TechnologyProposal;
		out validatedProposal : TechnologyProposal;
	}
	
	action def ConductEthicalAnalysis {
		in proposal : TechnologyProposal;
		out assessment : EthicalAssessment;
	}
	
	action def SynthesizeAssessment {
		in biasScore : BiasMetric;
		in privacyScore : PrivacyLevel;
		in transparencyScore : Real;
		in accountabilityScore : Real;
		out overallAssessment : EthicalAssessment;
	}
	
	action def RenderDecision {
		in assessment : EthicalAssessment;
		out decision : EthicalDecision;
	}
	
	action def EscalateForReview {
		in assessment : EthicalAssessment;
		in preliminaryDecision : EthicalDecision;
		out reviewedDecision : EthicalDecision;
	}
	
	action def IssueApproval {
		in decision : EthicalDecision;
		out approvalNotification : String;
	}
	
	action def EthicalEvaluationProcess {
		first start;
		
		then action receiveProposal : ReceiveProposal {
			in proposal;
			out validatedProposal;
		}
		
		then merge continuousEvaluation;
		
		then action conductAnalysis : ConductEthicalAnalysis {
			in proposal = receiveProposal.validatedProposal;
			out assessment;
		}
		
		then action synthesize : SynthesizeAssessment {
			in biasScore;
			in privacyScore;
			in transparencyScore;
			in accountabilityScore;
			out overallAssessment;
		}
		
		then action renderDecision : RenderDecision {
			in assessment = synthesize.overallAssessment;
			out decision;
		}
		
		then decide;
			if renderDecision.decision.outcome == EthicalDecisionKind::escalate then escalateReview;
			if renderDecision.decision.outcome == EthicalDecisionKind::approve then issueApproval;
			if renderDecision.decision.outcome == EthicalDecisionKind::reject then rejectProposal;
			if renderDecision.decision.outcome == EthicalDecisionKind::requireReview then escalateReview;
		
		action escalateReview : EscalateForReview {
			in assessment = synthesize.overallAssessment;
			in preliminaryDecision = renderDecision.decision;
			out reviewedDecision;
		}
		then decide;
			if escalateReview.reviewedDecision.outcome == EthicalDecisionKind::approve then issueApproval;
			if escalateReview.reviewedDecision.outcome == EthicalDecisionKind::reject then rejectProposal;
		
		action issueApproval : IssueApproval {
			in decision = renderDecision.decision;
			out approvalNotification;
		}
		then initiateMonitoring;
		
		action initiateMonitoring;
		then continuousEvaluation;
		
		action rejectProposal;
		then done;
	}
	
	action ethicalEvaluationProcess : EthicalEvaluationProcess;
	
	requirement def EthicalRequirement;
	
	requirement <'ETH-001'> fairnessRequirement : EthicalRequirement {
		doc /* The system shall ensure algorithmic fairness by detecting and mitigating 
		     bias across protected attributes with bias scores below 0.15 threshold. */
		
		subject system : EthicalGovernanceSystem;
		
		require constraint {
			system.biasEngine.biasThreshold <= 0.15 and
			system.biasEngine.algorithmicFairnessEnabled == true
		}
	}
	
	requirement <'ETH-002'> privacyRequirement : EthicalRequirement {
		doc /* Technology proposals shall undergo privacy impact analysis ensuring 
		     data minimization, encryption, and explicit consent mechanisms. */
		
		subject system : EthicalGovernanceSystem;
		
		require constraint {
			system.privacyAnalyzer.dataMinimizationRequired == true and
			system.privacyAnalyzer.consentMechanismRequired == true and
			system.privacyAnalyzer.retentionPolicyDefined == true
		}
	}
	
	requirement <'ETH-003'> transparencyRequirement : EthicalRequirement {
		doc /* All approved technologies shall provide explainability and maintain 
		     comprehensive audit trails for accountability. */
		
		subject system : EthicalGovernanceSystem;
		
		require constraint {
			system.transparencyEval.explainabilityRequired == true and
			system.transparencyEval.auditTrailMandatory == true and
			system.transparencyEval.userNotificationRequired == true
		}
	}
	
	requirement <'ETH-004'> accountabilityRequirement : EthicalRequirement {
		doc /* Clear responsibility chains and oversight mechanisms shall be established 
		     for all deployed technologies with defined remedy processes. */
		
		subject system : EthicalGovernanceSystem;
		
		require constraint {
			system.accountabilityFramework.responsibilityAssigned == true and
			system.accountabilityFramework.oversightMechanismDefined == true and
			system.accountabilityFramework.remedyProcessEstablished == true
		}
	}
	
	requirement <'ETH-005'> humanOversightRequirement : EthicalRequirement {
		doc /* High-risk technology proposals shall require mandatory human review 
		     with qualified reviewers having intervention authority. */
		
		subject system : EthicalGovernanceSystem;
		
		require constraint {
			system.decisionEngine.humanReviewRequired == true and
			system.humanOversight.interventionAuthority == true
		}
	}
	
	requirement <'ETH-006'> continuousMonitoringRequirement : EthicalRequirement {
		doc /* Approved technologies shall be subject to continuous monitoring with 
		     anomaly detection and active feedback loops for ongoing compliance. */
		
		subject system : EthicalGovernanceSystem;
		
		require constraint {
			system.monitoringSystem.anomalyDetectionEnabled == true and
			system.monitoringSystem.feedbackLoopActive == true
		}
	}
	
	requirement ethicalGovernanceMission {
		doc /* The Ethical Governance System shall evaluate technology proposals through 
		     comprehensive ethical analysis encompassing fairness, privacy, transparency, 
		     and accountability, rendering decisions with human oversight for high-risk 
		     cases, and maintaining continuous monitoring of deployed technologies to 
		     ensure ongoing compliance with ethical principles and regulatory requirements. */
		
		require fairnessRequirement;
		require privacyRequirement;
		require transparencyRequirement;
		require accountabilityRequirement;
		require humanOversightRequirement;
		require continuousMonitoringRequirement;
	}
}

// --- Test harness (auto-generated) ---
package ExecutionHarness {
    private import ScalarValues::*;
    private import ISQ::*;
    private import SI::*;
    private import 'Ethics of Technology System'::*;

    action orchestrator {
        item testAssessment : EthicalAssessment {
            attribute assessmentId = "";
            attribute biasScore : BiasMetric;
            attribute privacyScore : PrivacyLevel;
            attribute transparencyScore = 0.0;
            attribute accountabilityScore = 0.0;
            attribute fairnessScore = 0.0;
            attribute overallRisk : RiskLevel;
            attribute complianceLevel : ComplianceScore;
            attribute timestamp = "";
        }
        action escalateReviewProbe : EscalateForReview {
            in assessment = testAssessment;
            // TODO(human): unsupported input type for preliminaryDecision: EthicalDecision (unsupported structured payload members: outcome, conditions)
        }
        first escalateReviewProbe;
    }
}

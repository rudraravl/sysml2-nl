package 'Skin Electrode Gel System' {
	private import ScalarValues::*;
	private import ISQ::*;
	private import SI::*;
	
	attribute def ElectricalConductivityValue :> Real {
		doc /* Electrical conductivity in Siemens per meter (S/m) */
	}
	
	attribute def ViscosityValue :> Real {
		doc /* Dynamic viscosity in Pascal-seconds (Pa·s) */
	}
	
	attribute def ImpedanceValue :> Real {
		doc /* Electrical impedance in Ohms (Ω) */
	}
	
	attribute def pHValue :> Real {
		doc /* pH level of the gel, range 0-14 */
	}
	
	attribute def ContactQualityLevel :> String {
		doc /* Quality of skin-electrode contact: excellent, good, adequate, poor */
	}
	
	item def ElectrodeGel {
		doc /* Conductive gel formulation for reducing skin-electrode impedance */
		attribute conductivity : ElectricalConductivityValue;
		attribute viscosity : ViscosityValue;
		attribute pH : pHValue;
		attribute ionicConcentration : Real;
		attribute waterContent : Real;
		attribute chlorideContent : Real;
	}
	
	item def SkinSurface {
		doc /* Human skin surface with electrical and physical properties */
		attribute surfaceImpedance : ImpedanceValue;
		attribute moistureLevel : Real;
		attribute temperature : TemperatureValue;
		attribute surfaceArea : AreaValue;
	}
	
	item def BioelectricSignal {
		doc /* Electrical signal generated by biological activity */
		attribute amplitude : ElectricPotentialDifferenceValue;
		attribute frequency : Real;
		attribute signalToNoiseRatio : Real;
		attribute bandwidth : Real;
	}
	
	port def GelApplicationInterface {
		doc /* Interface for gel application to skin */
		out item dispensedGel : ElectrodeGel;
		in item targetSurface : SkinSurface;
		attribute applicationThickness : LengthValue;
	}
	
	port def ElectricalCouplingInterface {
		doc /* Interface for electrical signal transmission */
		in item sourceSignal : BioelectricSignal;
		out item transmittedSignal : BioelectricSignal;
		attribute interfaceImpedance : ImpedanceValue;
		attribute couplingEfficiency : Real;
	}
	
	port def SkinContactInterface {
		doc /* Interface between gel layer and skin */
		in item skin : SkinSurface;
		out contactQuality : ContactQualityLevel;
		attribute contactArea : AreaValue;
	}
	
	part def GelLayer {
		doc /* Conductive gel layer between skin and electrode */
		attribute thickness : LengthValue;
		attribute uniformity : Real;
		attribute composition : ElectrodeGel;
		attribute effectiveImpedance : ImpedanceValue;
		
		port skinContact : SkinContactInterface;
		port electricalInterface : ElectricalCouplingInterface;
	}
	
	part def ImpedanceReducer {
		doc /* Subsystem that reduces skin-electrode interface impedance */
		in attribute initialImpedance : ImpedanceValue;
		out attribute finalImpedance : ImpedanceValue;
		attribute reductionRatio : Real;
		
		port gelInput : GelApplicationInterface;
	}
	
	part def SignalCoupler {
		doc /* Subsystem that couples bioelectric signals through gel medium */
		in attribute inputSignal : BioelectricSignal;
		out attribute outputSignal : BioelectricSignal;
		attribute transmissionEfficiency : Real;
		attribute frequencyResponse : Real;
	}
	
	part def ContactStabilizer {
		doc /* Subsystem that maintains stable gel-skin contact */
		in attribute gelViscosity : ViscosityValue;
		in attribute skinMoisture : Real;
		out attribute stabilityIndex : Real;
	}
	
	action def ApplyGelToSkin {
		doc /* Apply electrode gel to prepared skin surface */
		in gel : ElectrodeGel;
		in skinArea : SkinSurface;
		in targetThickness : LengthValue;
		out gelLayer : GelLayer;
	}
	
	action def ReduceInterfaceImpedance {
		doc /* Reduce electrical impedance at skin-electrode interface */
		in gelLayer : GelLayer;
		in baselineImpedance : ImpedanceValue;
		out reducedImpedance : ImpedanceValue;
	}
	
	action def CoupleElectricalSignal {
		doc /* Couple bioelectric signal from skin through gel to electrode */
		in bioSignal : BioelectricSignal;
		in gelConductivity : ElectricalConductivityValue;
		in gelThickness : LengthValue;
		out coupledSignal : BioelectricSignal;
	}
	
	action def MaintainStableContact {
		doc /* Maintain stable physical and electrical contact over time */
		in gelProperties : ElectrodeGel;
		in environmentalConditions : Real;
		out contactQuality : ContactQualityLevel;
	}
	
	action def MonitorGelPerformance {
		doc /* Monitor gel performance metrics during operation */
		in currentImpedance : ImpedanceValue;
		in signalQuality : Real;
		out performanceStatus : String;
	}
	
	action def EnableBioelectricSignalAcquisition {
		doc /* Primary function: Enable high-quality bioelectric signal acquisition by reducing skin-electrode impedance */
		in attribute targetSkin : SkinSurface;
		in attribute gelFormulation : ElectrodeGel;
		in attribute desiredThickness : LengthValue;
		out attribute acquiredSignal : BioelectricSignal;
		out attribute finalImpedance : ImpedanceValue;
		out attribute contactStatus : ContactQualityLevel;
		
		first start;
		then action applyGel : ApplyGelToSkin {
			in gel = gelFormulation;
			in skinArea = targetSkin;
			in targetThickness = desiredThickness;
			out gelLayer;
		}
		then action reduceImpedance : ReduceInterfaceImpedance {
			in gelLayer = applyGel.gelLayer;
			in baselineImpedance = targetSkin.surfaceImpedance;
			out reducedImpedance;
		}
		then merge operationalLoop;
		then action maintainContact : MaintainStableContact {
			in gelProperties = gelFormulation;
			in environmentalConditions = targetSkin.temperature;
			out contactQuality;
		}
		then action coupleSignal : CoupleElectricalSignal {
			in bioSignal : BioelectricSignal;
			in gelConductivity = gelFormulation.conductivity;
			in gelThickness = applyGel.gelLayer.thickness;
			out coupledSignal;
		}
		then action monitorPerformance : MonitorGelPerformance {
			in currentImpedance = reduceImpedance.reducedImpedance;
			in signalQuality = coupleSignal.coupledSignal.signalToNoiseRatio;
			out performanceStatus;
		}
		then decide;
			if monitorPerformance.performanceStatus == "degraded" then applyGel;
			if monitorPerformance.performanceStatus == "acceptable" then assignOutputs;
		action assignOutputs {
			then assign acquiredSignal := coupleSignal.coupledSignal;
			then assign finalImpedance := reduceImpedance.reducedImpedance;
			then assign contactStatus := maintainContact.contactQuality;
		}
		then operationalLoop;
	}
	
	state def GelLifecycleStateMachine {
		doc /* State machine representing gel lifecycle from application to degradation */
		
		entry; then Stored;
		
		state Stored {
			doc /* Gel is stored in sealed container */
		}
		
		state Applied {
			doc /* Gel has been applied to skin surface */
		}
		
		state Active {
			doc /* Gel is actively conducting signals */
		}
		
		state Degrading {
			doc /* Gel properties are degrading over time */
		}
		
		state Depleted {
			doc /* Gel has lost effectiveness and requires replacement */
		}
		
		transition first Stored then Applied;
		transition Applied then Active;
		transition Active then Degrading;
		transition Degrading then Active;
		transition Degrading then Depleted;
		transition Depleted then Stored;
	}
	
	part def SkinElectrodeGelSystem {
		doc /* Complete system for enabling bioelectric signal acquisition through impedance reduction */
		
		part gelFormulation : ElectrodeGel {
			attribute conductivity = 8.5;
			attribute viscosity = 4.2;
			attribute pH = 7.0;
			attribute ionicConcentration = 0.12;
			attribute waterContent = 0.75;
			attribute chlorideContent = 0.08;
		}
		
		part impedanceReducer : ImpedanceReducer {
			attribute reductionRatio = 0.15;
		}
		
		part signalCoupler : SignalCoupler {
			attribute transmissionEfficiency = 0.92;
			attribute frequencyResponse = 1000.0;
		}
		
		part contactStabilizer : ContactStabilizer;
		
		part activeGelLayer : GelLayer {
			attribute thickness = 0.3 [SI::mm];
			attribute uniformity = 0.88;
			attribute composition = gelFormulation;
		}
		
		port applicationInterface : GelApplicationInterface;
		port couplingInterface : ElectricalCouplingInterface;
		
		perform action primaryFunction : EnableBioelectricSignalAcquisition {
			in attribute targetSkin : SkinSurface;
			in attribute gelFormulation = gelFormulation;
			in attribute desiredThickness = 0.3 [SI::mm];
			out attribute acquiredSignal : BioelectricSignal;
			out attribute finalImpedance : ImpedanceValue;
			out attribute contactStatus : ContactQualityLevel;
		}
		
		state gelLifecycle : GelLifecycleStateMachine;
		
		connection gelToImpedanceReducer connect 
			activeGelLayer.electricalInterface to impedanceReducer.gelInput;
		connection impedanceToSignalCoupler connect 
			impedanceReducer to signalCoupler;
	}
	
	requirement def <'REQ-001'> LowImpedanceRequirement {
		doc /* System shall reduce skin-electrode impedance to below 5 kΩ */
		subject system : SkinElectrodeGelSystem;
		require constraint {
			system.primaryFunction.finalImpedance < 5000.0
		}
	}
	
	requirement def <'REQ-002'> HighConductivityRequirement {
		doc /* Gel shall maintain electrical conductivity above 5 S/m */
		subject gel : ElectrodeGel;
		require constraint {
			gel.conductivity >= 5.0
		}
	}
	
	requirement def <'REQ-003'> BiocompatibilityRequirement {
		doc /* Gel shall maintain neutral pH for skin biocompatibility */
		subject gel : ElectrodeGel;
		require constraint {
			gel.pH >= 6.5 and gel.pH <= 7.5
		}
	}
	
	requirement def <'REQ-004'> SignalQualityRequirement {
		doc /* System shall maintain signal-to-noise ratio above 25 dB */
		subject system : SkinElectrodeGelSystem;
		require constraint {
			system.primaryFunction.acquiredSignal.signalToNoiseRatio >= 25.0
		}
	}
	
	requirement def <'REQ-005'> ContactStabilityRequirement {
		doc /* System shall maintain excellent or good contact quality */
		subject system : SkinElectrodeGelSystem;
		require constraint {
			system.primaryFunction.contactStatus == "excellent" or 
			system.primaryFunction.contactStatus == "good"
		}
	}
	
	requirement def <'REQ-006'> ViscosityRequirement {
		doc /* Gel viscosity shall be within range for proper application and adhesion */
		subject gel : ElectrodeGel;
		require constraint {
			gel.viscosity >= 3.0 and gel.viscosity <= 6.0
		}
	}
	
	requirement <'SYS-REQ-001'> systemRequirements {
		doc /* Top-level requirements for skin electrode gel system */
		
		require <'REQ-001'> lowImpedance : LowImpedanceRequirement;
		require <'REQ-002'> highConductivity : HighConductivityRequirement;
		require <'REQ-003'> biocompatibility : BiocompatibilityRequirement;
		require <'REQ-004'> signalQuality : SignalQualityRequirement;
		require <'REQ-005'> contactStability : ContactStabilityRequirement;
		require <'REQ-006'> viscosity : ViscosityRequirement;
	}
	
	part electrodeGelSystem : SkinElectrodeGelSystem {
		doc /* Instantiated skin electrode gel system for bioelectric signal acquisition */
		
		satisfy systemRequirements.lowImpedance by impedanceReducer;
		satisfy systemRequirements.highConductivity by gelFormulation;
		satisfy systemRequirements.biocompatibility by gelFormulation;
		satisfy systemRequirements.signalQuality by signalCoupler;
		satisfy systemRequirements.contactStability by contactStabilizer;
		satisfy systemRequirements.viscosity by gelFormulation;
	}
}

// --- Test harness (auto-generated) ---
package ExecutionHarness {
    private import ScalarValues::*;
    private import ISQ::*;
    private import SI::*;
    private import 'Skin Electrode Gel System'::*;

    part testSubject : GelLayer {
        exhibit state sm : GelLifecycleStateMachine;
    }

    action orchestrator {
        item testGel : ElectrodeGel {
            attribute conductivity : ElectricalConductivityValue = 0.0;
            attribute viscosity : ViscosityValue = 0.0;
            attribute pH : pHValue = 0.0;
            attribute ionicConcentration = 0.0;
            attribute waterContent = 0.0;
            attribute chlorideContent = 0.0;
        }
        item testSkinArea : SkinSurface {
            attribute surfaceImpedance : ImpedanceValue = 0.0;
            attribute moistureLevel = 0.0;
            attribute temperature : TemperatureValue;
            attribute surfaceArea : AreaValue;
        }
        attribute testTargetThickness : LengthValue;
        action actionProbe : ApplyGelToSkin {
            in gel = testGel;
            in skinArea = testSkinArea;
            in targetThickness = testTargetThickness;
        }
        first actionProbe;
    }
}

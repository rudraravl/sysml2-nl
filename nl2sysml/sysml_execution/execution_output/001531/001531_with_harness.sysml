package 'Platform Fragmentation System' {
	private import ScalarValues::*;
	private import ISQ::*;
	private import SI::*;
	
	attribute def PlatformIdentifier;
	attribute def APIVersion;
	attribute def CompatibilityIndex :> Real;
	
	attribute def FragmentationScore :> Real;
	
	attribute def AdaptationTime :> ISQ::DurationValue;
	
	attribute def CoveragePercentage :> Real;
	
	item def ApplicationComponent {
		attribute componentId : String;
		attribute baseVersion : APIVersion;
		attribute supportedPlatforms : PlatformIdentifier[*];
	}
	
	item def PlatformInstance {
		attribute platformId : PlatformIdentifier;
		attribute apiVersion : APIVersion;
		attribute marketShare : Real;
		attribute deviceCount : Integer;
	}
	
	item def AdaptationPackage {
		attribute sourceComponent : ApplicationComponent;
		attribute targetPlatform : PlatformInstance;
		attribute adaptationStatus : String;
	}
	
	port def PlatformDiscoveryPort {
		in item platformData : PlatformInstance[*];
		out item discoveredPlatforms : PlatformInstance[*];
	}
	
	port def FragmentationAnalysisPort {
		in item platforms : PlatformInstance[*];
		out attribute fragmentationLevel : FragmentationScore;
		out item criticalPlatforms : PlatformInstance[*];
	}
	
	port def AdaptationPort {
		in item component : ApplicationComponent;
		in item targetPlatform : PlatformInstance;
		out item adaptedPackage : AdaptationPackage;
	}
	
	port def ValidationPort {
		in item package : AdaptationPackage;
		out attribute isValid : Boolean;
		out attribute coverage : CoveragePercentage;
	}
	
	part def PlatformDiscoveryModule {
		port discoveryPort : PlatformDiscoveryPort;
		
		perform action discoverPlatforms {
			in rawPlatformData : PlatformInstance[*];
			out activePlatforms : PlatformInstance[*];
			out platformCount : Integer;
		}
	}
	
	part def FragmentationAnalysisModule {
		port analysisPort : FragmentationAnalysisPort;
		
		perform action analyzeFragmentation {
			in detectedPlatforms : PlatformInstance[*];
			out fragmentationScore : FragmentationScore;
			out highPriorityPlatforms : PlatformInstance[*];
			out diversityMetric : Real;
		}
	}
	
	part def ComponentAdaptationModule {
		port adaptationPort : AdaptationPort;
		
		perform action adaptComponentToPlatform {
			in originalComponent : ApplicationComponent;
			in targetPlatform : PlatformInstance;
			out adaptedPackage : AdaptationPackage;
			out adaptationEffort : AdaptationTime;
		}
	}
	
	part def CompatibilityValidationModule {
		port validationPort : ValidationPort;
		
		perform action validateCompatibility {
			in adaptationPackage : AdaptationPackage;
			in targetPlatform : PlatformInstance;
			out validationResult : Boolean;
			out coverageScore : CoveragePercentage;
			out issues : String[*];
		}
	}
	
	state def FragmentationManagementStates {
		entry; then monitoring;
		
		state monitoring {
			entry action setMonitoringPhase {
				assign currentPhase = "Monitoring Ecosystem";
			}
			do action continuousMonitoring;
		}
		
		accept fragmentationDetected;
		then analyzing;
		
		state analyzing {
			entry action setAnalyzingPhase {
				assign currentPhase = "Analyzing Fragmentation";
			}
			do action performFragmentationAnalysis;
		}
		
		accept analysisComplete;
		if fragmentationScore > thresholdLevel then adapting
		else monitoring;
		
		state adapting {
			entry action setAdaptingPhase {
				assign currentPhase = "Adapting Components";
			}
			do action executeAdaptation;
		}
		
		accept adaptationComplete;
		then validating;
		
		state validating {
			entry action setValidatingPhase {
				assign currentPhase = "Validating Adaptations";
			}
			do action performValidation;
		}
		
		accept validationComplete;
		if allValid then deploying
		else adapting;
		
		state deploying {
			entry action setDeployingPhase {
				assign currentPhase = "Deploying Adaptations";
			}
			do action deployAdaptedComponents;
		}
		
		accept deploymentComplete;
		then monitoring;
		
		attribute currentPhase : String;
		attribute fragmentationScore : FragmentationScore;
		attribute thresholdLevel : FragmentationScore;
		attribute allValid : Boolean;
	}
	
	action def ManageFragmentation {
		in attribute ecosystemPlatforms : PlatformInstance[*];
		in attribute applicationComponents : ApplicationComponent[*];
		in attribute fragmentationThreshold : FragmentationScore;
		out attribute adaptedComponents : AdaptationPackage[*];
		out attribute systemFragmentation : FragmentationScore;
		out attribute platformCoverage : CoveragePercentage;
		
		first start;
		then action gatherPlatformData {
			in platforms = ecosystemPlatforms;
			out platformInventory : PlatformInstance[*];
			out totalPlatforms : Integer;
		}
		
		then action evaluateFragmentation {
			in inventory = gatherPlatformData.platformInventory;
			out currentFragmentation : FragmentationScore;
			out targetPlatforms : PlatformInstance[*];
			out fragmentationTrend : Real;
		}
		
		then decide;
		if evaluateFragmentation.currentFragmentation > fragmentationThreshold then initiateAdaptationCycle;
		if evaluateFragmentation.currentFragmentation <= fragmentationThreshold then maintainMonitoring;
		
		action initiateAdaptationCycle {
			first beginAdaptation;
			then merge processNextComponent;
			
			action processNextComponent;
			then action selectComponentForAdaptation {
				in components = applicationComponents;
				out selectedComponent : ApplicationComponent;
				out remainingComponents : ApplicationComponent[*];
			}
			
			then action createAdaptations {
				in component = selectComponentForAdaptation.selectedComponent;
				in platforms = evaluateFragmentation.targetPlatforms;
				out adaptationSet : AdaptationPackage[*];
				out adaptationDuration : AdaptationTime;
			}
			
			then action validateAdaptationSet {
				in adaptations = createAdaptations.adaptationSet;
				in platforms = evaluateFragmentation.targetPlatforms;
				out validatedAdaptations : AdaptationPackage[*];
				out validationResults : Boolean[*];
				out overallCoverage : CoveragePercentage;
			}
			
			then action recordAdaptations {
				in validated = validateAdaptationSet.validatedAdaptations;
				out recorded : AdaptationPackage[*];
			}
			
			then decide;
			if selectComponentForAdaptation.remainingComponents->size() > 0 then processNextComponent;
			else finalizeAdaptation;
			
			action finalizeAdaptation {
				in allAdaptations = recordAdaptations.recorded;
				out finalAdaptations : AdaptationPackage[*];
				out finalCoverage : CoveragePercentage;
			}
			then convergeManagement;
		}
		
		action maintainMonitoring {
			in fragmentation = evaluateFragmentation.currentFragmentation;
			out monitoringStatus : String;
			out nextCheckTime : ISQ::DurationValue;
		}
		then convergeManagement;
		
		merge convergeManagement;
		then assign adaptedComponents := initiateAdaptationCycle.finalizeAdaptation.finalAdaptations;
		then assign systemFragmentation := evaluateFragmentation.currentFragmentation;
		then assign platformCoverage := initiateAdaptationCycle.finalizeAdaptation.finalCoverage;
		then done;
	}
	
	part def PlatformFragmentationManagementSystem {
		doc /*
			The Platform Fragmentation Management System addresses the challenge of 
			software compatibility across diverse and evolving platform variants.
			
			Its primary function is to continuously monitor the platform ecosystem,
			detect fragmentation patterns, and automatically adapt application components
			to ensure broad compatibility and optimal user coverage. The system analyzes
			platform diversity, prioritizes adaptation efforts based on market impact,
			and validates all adaptations to maintain functional integrity across the
			fragmented landscape.
			
			By managing fragmentation proactively, the system minimizes development
			overhead, maximizes platform reach, and ensures consistent application
			behavior across heterogeneous deployment environments.
		*/
		
		attribute systemIdentifier : String;
		attribute operationalMode : String;
		
		part discoveryModule : PlatformDiscoveryModule;
		part analysisModule : FragmentationAnalysisModule;
		part adaptationModule : ComponentAdaptationModule[1..*];
		part validationModule : CompatibilityValidationModule;
		
		connection discoveryToAnalysis connect 
			discoveryModule.discoveryPort.discoveredPlatforms 
			to analysisModule.analysisPort.platforms;
		
		connection analysisToAdaptation connect 
			analysisModule.analysisPort.criticalPlatforms 
			to adaptationModule.adaptationPort.targetPlatform;
		
		connection adaptationToValidation connect 
			adaptationModule.adaptationPort.adaptedPackage 
			to validationModule.validationPort.package;
		
		perform action manageFragmentation : ManageFragmentation {
			in ecosystemPlatforms : PlatformInstance[*];
			in applicationComponents : ApplicationComponent[*];
			in fragmentationThreshold : FragmentationScore;
			out adaptedComponents : AdaptationPackage[*];
			out systemFragmentation : FragmentationScore;
			out platformCoverage : CoveragePercentage;
		}
		
		perform state fragmentationStateMachine : FragmentationManagementStates;
	}
	
	requirement def FragmentationManagementRequirement {
		doc /* Core requirements for managing platform fragmentation effectively. */
		
		subject system : PlatformFragmentationManagementSystem;
		
		require constraint maxFragmentation {
			doc /* System fragmentation score shall not exceed 0.80. */
			system.manageFragmentation.systemFragmentation <= 0.80
		}
		
		require constraint minCoverage {
			doc /* Platform coverage shall be at least 85%. */
			system.manageFragmentation.platformCoverage >= 0.85
		}
	}
	
	requirement <'REQ-001'> detectAllPlatforms : FragmentationManagementRequirement {
		doc /* The system shall detect all active platform variants in the ecosystem. */
		
		assume constraint platformDataAccessible {
			doc /* Platform discovery data is available and current. */
		}
		
		require constraint completePlatformInventory {
			doc /* All platforms with >1% market share shall be detected. */
		}
	}
	
	requirement <'REQ-002'> quantifyFragmentation : FragmentationManagementRequirement {
		doc /* The system shall accurately quantify fragmentation levels. */
		
		require constraint accurateMetrics {
			doc /* Fragmentation metrics shall reflect platform API diversity. */
		}
		
		require constraint trendAnalysis {
			doc /* System shall track fragmentation trends over time. */
		}
	}
	
	requirement <'REQ-003'> automaticAdaptation : FragmentationManagementRequirement {
		doc /* The system shall automatically adapt components to target platforms. */
		
		require constraint preserveSemantics {
			doc /* Adapted components shall preserve original functionality. */
		}
		
		require constraint efficientAdaptation {
			doc /* Adaptation time shall be minimized through intelligent reuse. */
		}
	}
	
	requirement <'REQ-004'> validateAllAdaptations : FragmentationManagementRequirement {
		doc /* The system shall validate compatibility of all adaptations. */
		
		require constraint comprehensiveValidation {
			doc /* All critical platform-component pairs shall be validated. */
		}
		
		require constraint reportIssues {
			doc /* Validation failures shall be reported with diagnostic details. */
		}
	}
	
	part fragmentationSystem : PlatformFragmentationManagementSystem {
		redefines systemIdentifier = "PFMS-2024-001";
		redefines operationalMode = "Active";
		
		satisfy detectAllPlatforms;
		satisfy quantifyFragmentation;
		satisfy automaticAdaptation;
		satisfy validateAllAdaptations;
	}
}

// --- Test harness (auto-generated) ---
package ExecutionHarness {
    private import ScalarValues::*;
    private import ISQ::*;
    private import SI::*;
    private import 'Platform Fragmentation System'::*;

    part testSubject : PlatformDiscoveryModule {
        exhibit state sm : FragmentationManagementStates;
    }

    action orchestrator {
        attribute testFragmentationThreshold : FragmentationScore = 0.0;
        action actionProbe : ManageFragmentation {
            // TODO(human): unsupported input type for ecosystemPlatforms: PlatformInstance[*] (type is not a primitive, enum, extracted payload def, or known value type)
            // TODO(human): unsupported input type for applicationComponents: ApplicationComponent[*] (type is not a primitive, enum, extracted payload def, or known value type)
            in fragmentationThreshold = testFragmentationThreshold;
            // TODO(human): unsupported input type for platforms: unknown (missing declared type)
            // TODO(human): unsupported input type for inventory: unknown (missing declared type)
            // TODO(human): unsupported input type for components: unknown (missing declared type)
            // TODO(human): unsupported input type for component: unknown (missing declared type)
            // TODO(human): unsupported input type for platforms: unknown (missing declared type)
            // TODO(human): unsupported input type for adaptations: unknown (missing declared type)
            // TODO(human): unsupported input type for platforms: unknown (missing declared type)
            // TODO(human): unsupported input type for validated: unknown (missing declared type)
            // TODO(human): unsupported input type for allAdaptations: unknown (missing declared type)
            // TODO(human): unsupported input type for fragmentation: unknown (missing declared type)
        }
        first actionProbe;
    }
}

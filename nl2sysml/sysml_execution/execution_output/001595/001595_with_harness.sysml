package 'Quantum Computing System' {
	private import ScalarValues::*;
	private import ISQ::*;
	private import SI::*;
	
	attribute def QubitState;
	attribute def QuantumGateSequence;
	attribute def MeasurementResult;
	attribute def AlgorithmSpecification;
	attribute def ErrorCorrectionCode;
	
	attribute def Temperature :> ISQ::ThermodynamicTemperatureValue;
	attribute def Fidelity :> Real;
	attribute def CoherenceTime :> ISQ::TimeValue;
	attribute def ErrorRate :> Real;
	
	item def QuantumAlgorithm {
		attribute gateSequence : QuantumGateSequence;
		attribute qubitCount : Integer;
		attribute expectedRuntime : ISQ::TimeValue;
	}
	
	item def ComputationResult {
		attribute bitString : Boolean[*];
		attribute confidence : Fidelity;
		attribute executionTime : ISQ::TimeValue;
	}
	
	part def CryogenicCoolingSystem {
		attribute operatingTemperature : Temperature;
		attribute coolingPower : ISQ::PowerValue;
		port thermalOut;
		
		action def MaintainTemperature {
			in targetTemp : Temperature;
			out currentTemp : Temperature;
		}
	}
	
	part def QuantumProcessingUnit {
		attribute qubitCount : Integer;
		attribute gateErrorRate : ErrorRate;
		attribute coherenceTime : CoherenceTime;
		attribute operatingTemp : Temperature;
		
		port controlIn;
		port measurementOut;
		port thermalInterface;
		
		action def InitializeQubits {
			in numQubits : Integer;
			out initialState : QubitState;
		}
		
		action def ApplyQuantumGates {
			in state : QubitState;
			in gates : QuantumGateSequence;
			out evolvedState : QubitState;
		}
		
		action def MeasureQubits {
			in state : QubitState;
			out rawMeasurement : MeasurementResult;
		}
	}
	
	part def ClassicalControlSystem {
		attribute processingPower : ISQ::PowerValue;
		attribute memoryCapacity : ISQ::LengthValue;
		
		port algorithmInput;
		port quantumControl;
		port measurementInput;
		port resultOutput;
		
		action def CompileAlgorithm {
			in algorithm : QuantumAlgorithm;
			out gateSequence : QuantumGateSequence;
		}
		
		action def GenerateControlSignals {
			in gates : QuantumGateSequence;
			out controlPulses : Real[*];
		}
		
		action def ProcessMeasurements {
			in rawData : MeasurementResult;
			out result : ComputationResult;
		}
	}
	
	part def ErrorCorrectionUnit {
		attribute correctionThreshold : ErrorRate;
		attribute redundancyFactor : Integer;
		
		port dataIn;
		port dataOut;
		
		action def DetectErrors {
			in measurement : MeasurementResult;
			out errorSyndrome : ErrorCorrectionCode;
		}
		
		action def CorrectErrors {
			in syndrome : ErrorCorrectionCode;
			in rawData : MeasurementResult;
			out correctedData : MeasurementResult;
		}
	}
	
	part def ReadoutSystem {
		attribute readoutFidelity : Fidelity;
		attribute integrationTime : ISQ::TimeValue;
		
		port quantumSignalIn;
		port classicalDataOut;
		
		action def AmplifySignal {
			in quantumSignal : Real;
			out amplifiedSignal : Real;
		}
		
		action def Digitize {
			in analogSignal : Real;
			out digitalData : MeasurementResult;
		}
	}
	
	action def ExecuteQuantumComputation {
		in algorithm : QuantumAlgorithm;
		out computationResult : ComputationResult;
		
		first start;
		then action coolSystem : CryogenicCoolingSystem::MaintainTemperature {
			in targetTemp;
			out currentTemp;
		}
		then action compile : ClassicalControlSystem::CompileAlgorithm {
			in algorithm = ExecuteQuantumComputation::algorithm;
			out gateSequence;
		}
		then action initialize : QuantumProcessingUnit::InitializeQubits {
			in numQubits = algorithm.qubitCount;
			out initialState;
		}
		then action applyGates : QuantumProcessingUnit::ApplyQuantumGates {
			in state = initialize.initialState;
			in gates = compile.gateSequence;
			out evolvedState;
		}
		then action measure : QuantumProcessingUnit::MeasureQubits {
			in state = applyGates.evolvedState;
			out rawMeasurement;
		}
		then action detectErrors : ErrorCorrectionUnit::DetectErrors {
			in measurement = measure.rawMeasurement;
			out errorSyndrome;
		}
		then action correctErrors : ErrorCorrectionUnit::CorrectErrors {
			in syndrome = detectErrors.errorSyndrome;
			in rawData = measure.rawMeasurement;
			out correctedData;
		}
		then action processResults : ClassicalControlSystem::ProcessMeasurements {
			in rawData = correctErrors.correctedData;
			out result;
		}
		then assign computationResult := processResults.result;
		then done;
	}
	
	requirement def QuantumComputingRequirements {
		doc /* The quantum computing system shall maintain quantum coherence and 
		       execute quantum algorithms with sufficient fidelity to achieve 
		       quantum advantage over classical computation. */
		
		requirement <'QC-REQ-001'> coherenceRequirement {
			doc /* Qubits shall maintain coherence for sufficient duration to 
			       enable execution of multi-gate quantum circuits. */
			subject qpu : QuantumProcessingUnit;
			assume constraint {
				qpu.coherenceTime >= 100.0e-6 [SI::s]
			}
		}
		
		requirement <'QC-REQ-002'> errorRateRequirement {
			doc /* Quantum gate operations shall achieve error rates below 
			       threshold required for quantum error correction. */
			subject qpu : QuantumProcessingUnit;
			require constraint {
				qpu.gateErrorRate <= 0.001
			}
		}
		
		requirement <'QC-REQ-003'> temperatureRequirement {
			doc /* System shall operate at cryogenic temperatures to minimize 
			       thermal decoherence and maintain quantum states. */
			subject qpu : QuantumProcessingUnit;
			require constraint {
				qpu.operatingTemp <= 0.1 [SI::K]
			}
		}
		
		requirement <'QC-REQ-004'> fidelityRequirement {
			doc /* Measurement and readout operations shall achieve fidelity 
			       sufficient for reliable quantum computation. */
			subject readout : ReadoutSystem;
			require constraint {
				readout.readoutFidelity >= 0.99
			}
		}
		
		requirement <'QC-REQ-005'> scalabilityRequirement {
			doc /* System shall support sufficient qubit count to demonstrate 
			       quantum advantage for practical algorithms. */
			subject qpu : QuantumProcessingUnit;
			require constraint {
				qpu.qubitCount >= 100
			}
		}
	}
	
	part quantumComputingSystem {
		doc /* A quantum computing system leverages quantum mechanical phenomena 
		       including superposition and entanglement to perform computational 
		       operations intractable for classical computers. The system maintains 
		       qubits in quantum states at cryogenic temperatures, applies precisely 
		       controlled quantum gate operations to manipulate these states according 
		       to quantum algorithms, and performs measurements to extract classical 
		       computational results. Its primary function is to execute quantum 
		       algorithms that solve complex optimization, simulation, and 
		       cryptographic problems exponentially faster than classical approaches. */
		
		satisfy quantumRequirements : QuantumComputingRequirements;
		
		part cryoSystem : CryogenicCoolingSystem {
			attribute :>> operatingTemperature = 0.015 [SI::K];
			attribute :>> coolingPower = 2.0 [SI::W];
		}
		
		part qpu : QuantumProcessingUnit {
			attribute :>> qubitCount = 127;
			attribute :>> gateErrorRate = 0.0008;
			attribute :>> coherenceTime = 150.0e-6 [SI::s];
			attribute :>> operatingTemp = 0.015 [SI::K];
		}
		
		part classicalControl : ClassicalControlSystem {
			attribute :>> processingPower = 500.0 [SI::W];
			attribute :>> memoryCapacity = 1.0e12 [SI::m];
		}
		
		part errorCorrection : ErrorCorrectionUnit {
			attribute :>> correctionThreshold = 0.01;
			attribute :>> redundancyFactor = 5;
		}
		
		part readout : ReadoutSystem {
			attribute :>> readoutFidelity = 0.993;
			attribute :>> integrationTime = 1.0e-6 [SI::s];
		}
		
		connect cryoSystem.thermalOut to qpu.thermalInterface;
		connect classicalControl.quantumControl to qpu.controlIn;
		connect qpu.measurementOut to readout.quantumSignalIn;
		connect readout.classicalDataOut to errorCorrection.dataIn;
		connect errorCorrection.dataOut to classicalControl.measurementInput;
		
		perform action executeComputation : ExecuteQuantumComputation[*] ordered {
			in algorithm;
			out computationResult;
		}
		
		state def OperationalStates {
			entry; then offline;
			
			state offline;
			accept StartCooling;
			then cooling;
			
			state cooling {
				entry assign cryoSystem.operatingTemperature := 0.015 [SI::K];
			}
			accept TemperatureReached;
			then ready;
			
			state ready {
				entry assign qpu.operatingTemp := cryoSystem.operatingTemperature;
			}
			accept AlgorithmReceived;
			then executing;
			
			state executing {
				do executeComputation;
			}
			accept ComputationComplete;
			then measuring;
			
			state measuring {
				do readout.Digitize;
			}
			accept MeasurementComplete;
			then errorCorrecting;
			
			state errorCorrecting {
				do errorCorrection.CorrectErrors;
			}
			accept CorrectionComplete;
			then ready;
			
			accept Shutdown;
			then offline;
			
			state fault;
			accept SystemFault;
			then fault;
		}
		
		exhibit systemBehavior : OperationalStates;
	}
}

// --- Test harness (auto-generated) ---
package ExecutionHarness {
    private import ScalarValues::*;
    private import ISQ::*;
    private import SI::*;
    private import 'Quantum Computing System'::*;

    part testSubject : CryogenicCoolingSystem {
        exhibit state sm : OperationalStates;
    }

    action orchestrator {
        attribute testTargetTemp : Temperature;
        action actionProbe : MaintainTemperature {
            in targetTemp = testTargetTemp;
        }
        first actionProbe;
    }
}

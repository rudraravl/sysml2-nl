package TechnologyScoutingSystem {
    private import ScalarValues::*;
    private import ISQ::*;
    private import SI::*;
    
    attribute def TechnologyReadinessLevel {
        attribute level : Integer;
        assert constraint { level >= 1 and level <= 9 }
    }
    
    attribute def RelevanceScore {
        attribute score : Real;
        assert constraint { score >= 0.0 and score <= 10.0 }
    }
    
    attribute def ConfidenceLevel {
        attribute confidence : Real;
        assert constraint { confidence >= 0.0 and confidence <= 1.0 }
    }
    
    item def TechnologySignal {
        attribute sourceIdentifier : ScalarValues::String;
        attribute sourceType : ScalarValues::String;
        attribute captureTimestamp : ScalarValues::String;
        attribute rawContent : ScalarValues::String;
        attribute initialRelevance : ScalarValues::Real;
    }
    
    item def TechnologyCandidate {
        attribute candidateId : ScalarValues::String;
        attribute technologyName : ScalarValues::String;
        attribute description : ScalarValues::String;
        attribute domain : ScalarValues::String;
        attribute maturityLevel : TechnologyReadinessLevel;
        attribute relevanceScore : RelevanceScore;
        attribute confidenceLevel : ConfidenceLevel;
        attribute identificationDate : ScalarValues::String;
        attribute potentialApplications : ScalarValues::String[1..*];
        attribute competitiveImpact : ScalarValues::String;
    }
    
    item def AssessmentCriteria {
        attribute technicalFeasibility : ScalarValues::Real;
        attribute marketPotential : ScalarValues::Real;
        attribute strategicAlignment : ScalarValues::Real;
        attribute implementationCost : ScalarValues::Real;
        attribute timeToMarket : ScalarValues::Real;
    }
    
    item def ScoutingReport {
        attribute reportId : ScalarValues::String;
        attribute generationDate : ScalarValues::String;
        attribute reportingPeriod : ScalarValues::String;
        attribute executiveSummary : ScalarValues::String;
        attribute topCandidates : TechnologyCandidate[1..*] ordered;
        attribute trendAnalysis : ScalarValues::String;
        attribute recommendations : ScalarValues::String[1..*];
        attribute nextActions : ScalarValues::String[1..*];
    }
    
    port def SignalInputPort {
        in item signals : TechnologySignal[*];
    }
    
    port def CandidateOutputPort {
        out item candidates : TechnologyCandidate[*];
    }
    
    port def ReportOutputPort {
        out item report : ScoutingReport;
    }
    
    port def AnalysisDataPort {
        in item candidateData : TechnologyCandidate;
        out item assessmentResult : AssessmentCriteria;
    }
    
    port def RepositoryAccessPort {
        in item query : ScalarValues::String;
        out item results : TechnologyCandidate[*];
    }
    
    part def DataCollectionModule {
        doc /* Continuously monitors multiple information sources including
             * patent databases, research publications, industry reports,
             * conference proceedings, and startup ecosystems to capture
             * technology signals. */
        
        port signalInput : SignalInputPort;
        port candidateOutput : CandidateOutputPort;
        
        attribute monitoredSources : ScalarValues::Integer;
        attribute collectionFrequency : ISQ::DurationValue;
        attribute signalProcessingRate : ScalarValues::Real;
        
        action collectSignals {
            in sourceChannels : ScalarValues::String[*];
            out capturedSignals : TechnologySignal[*];
        }
        
        action filterSignals {
            in rawSignals : TechnologySignal[*];
            in filterCriteria : ScalarValues::String[*];
            out relevantSignals : TechnologySignal[*];
        }
    }
    
    part def AnalysisEngine {
        doc /* Applies multi-criteria evaluation framework to assess
             * technology candidates against strategic objectives,
             * technical feasibility, and market dynamics. */
        
        port analysisInput : AnalysisDataPort;
        
        attribute evaluationFramework : ScalarValues::String[1..*];
        attribute benchmarkDatabase : ScalarValues::String;
        attribute analysisAlgorithm : ScalarValues::String;
        
        action evaluateTechnology {
            in candidate : TechnologyCandidate;
            in criteria : AssessmentCriteria;
            out evaluatedCandidate : TechnologyCandidate;
            out assessmentScore : ScalarValues::Real;
        }
        
        action compareTechnologies {
            in candidates : TechnologyCandidate[*];
            out comparativeAnalysis : ScalarValues::String;
        }
    }
    
    part def PrioritizationModule {
        doc /* Ranks technology candidates based on weighted scoring
             * across multiple dimensions to identify highest-value
             * opportunities for strategic investment. */
        
        attribute priorityWeights : ScalarValues::Real[1..*];
        attribute rankingThreshold : ScalarValues::Real;
        attribute maxPriorityItems : ScalarValues::Integer;
        
        action rankCandidates {
            in assessedCandidates : TechnologyCandidate[*];
            in weightingFactors : ScalarValues::Real[*];
            out rankedList : TechnologyCandidate[*] ordered;
        }
        
        action identifyHighPriority {
            in rankedCandidates : TechnologyCandidate[*];
            out priorityCandidates : TechnologyCandidate[*];
        }
    }
    
    part def ReportingModule {
        doc /* Generates comprehensive scouting reports with visualizations,
             * trend analysis, and actionable recommendations for
             * technology leadership and strategic planning teams. */
        
        port reportOutput : ReportOutputPort;
        
        attribute reportTemplate : ScalarValues::String;
        attribute visualizationFormat : ScalarValues::String;
        attribute distributionList : ScalarValues::String[1..*];
        
        action compileReport {
            in prioritizedCandidates : TechnologyCandidate[*];
            in analysisData : ScalarValues::String;
            in trendData : ScalarValues::String;
            out finalReport : ScoutingReport;
        }
        
        action distributeReport {
            in report : ScoutingReport;
            in recipients : ScalarValues::String[*];
        }
    }
    
    part def KnowledgeRepository {
        doc /* Maintains historical database of all identified technologies,
             * assessments, and outcomes to support trend analysis,
             * pattern recognition, and continuous learning. */
        
        port repositoryAccess : RepositoryAccessPort;
        
        attribute databaseCapacity : ScalarValues::Integer;
        attribute retentionPeriod : ISQ::DurationValue;
        attribute lastUpdateTimestamp : ScalarValues::String;
        
        action storeCandidate {
            in candidate : TechnologyCandidate;
            in metadata : ScalarValues::String;
        }
        
        action retrieveHistory {
            in searchQuery : ScalarValues::String;
            in timeRange : ScalarValues::String;
            out historicalData : TechnologyCandidate[*];
        }
        
        action analyzeTrends {
            in domain : ScalarValues::String;
            in timePeriod : ScalarValues::String;
            out trendReport : ScalarValues::String;
        }
    }
    
    part def StakeholderInterface {
        doc /* Provides interactive dashboard and notification system
             * for technology leaders to review findings, provide feedback,
             * and initiate follow-up actions. */
        
        attribute dashboardUrl : ScalarValues::String;
        attribute notificationChannels : ScalarValues::String[1..*];
        attribute userAccessLevel : ScalarValues::String;
        
        action displayDashboard {
            in reportData : ScoutingReport;
        }
        
        action sendNotification {
            in alertType : ScalarValues::String;
            in message : ScalarValues::String;
            in recipients : ScalarValues::String[*];
        }
    }
    
    action def MonitorInformationSources {
        in monitoringChannels : ScalarValues::String[*];
        in monitoringParameters : ScalarValues::String;
        out rawSignals : TechnologySignal[*];
    }
    
    action def FilterAndExtract {
        in rawSignals : TechnologySignal[*];
        in relevanceCriteria : ScalarValues::String[*];
        out filteredSignals : TechnologySignal[*];
        out extractedCandidates : TechnologyCandidate[*];
    }
    
    action def AssessCandidate {
        in candidate : TechnologyCandidate;
        in assessmentCriteria : AssessmentCriteria;
        out assessedCandidate : TechnologyCandidate;
        out assessmentScore : ScalarValues::Real;
    }
    
    action def PrioritizeOpportunities {
        in assessedCandidates : TechnologyCandidate[*];
        in prioritizationWeights : ScalarValues::Real[*];
        out prioritizedCandidates : TechnologyCandidate[*] ordered;
    }
    
    action def GenerateInsights {
        in prioritizedCandidates : TechnologyCandidate[*];
        in historicalContext : ScalarValues::String;
        out scoutingReport : ScoutingReport;
    }
    
    action def DeliverRecommendations {
        in report : ScoutingReport;
        in stakeholders : ScalarValues::String[*];
    }
    
    action def TechnologyScoutingCycle {
        doc /* Continuous process that monitors technology landscape,
             * identifies emerging opportunities, evaluates strategic fit,
             * and delivers actionable intelligence to decision-makers. */
        
        first start;
        then merge continuousMonitoring;
        
        action monitor : MonitorInformationSources {
            out technologySignals : TechnologySignal[*];
        }
        
        then action filterExtract : FilterAndExtract {
            in rawSignals = monitor.technologySignals;
            out candidates : TechnologyCandidate[*];
        }
        
        then decide;
            if filterExtract.candidates->size() > 0 then assessPhase;
            if filterExtract.candidates->size() == 0 then continuousMonitoring;
        
        action assessPhase : AssessCandidate[*] {
            in candidate : TechnologyCandidate;
            out evaluatedCandidate : TechnologyCandidate;
        }
        
        then action prioritize : PrioritizeOpportunities {
            in assessedCandidates = assessPhase.evaluatedCandidate;
            out topCandidates : TechnologyCandidate[*] ordered;
        }
        
        then action generateInsights : GenerateInsights {
            in prioritizedCandidates = prioritize.topCandidates;
            out report : ScoutingReport;
        }
        
        then action deliver : DeliverRecommendations {
            in report = generateInsights.report;
        }
        
        then continuousMonitoring;
        then done;
    }
    
    state def ScoutingSystemStates {
        doc /* State machine governing the operational modes of the
             * technology scouting system throughout its lifecycle. */
        
        entry; then initializing;
        
        state initializing {
            entry; then loadingConfiguration;
            state loadingConfiguration;
            transition loadingConfiguration_to_ready
                first loadingConfiguration
                then ready;
        }
        
        state ready;
        transition ready_to_active
            first ready
            then active;
        
        state active {
            entry; then monitoring;
            
            state monitoring {
                entry; then collectingData;
                state collectingData;
                transition collectingData_to_filtering
                    first collectingData
                    then filtering;
                state filtering;
                transition filtering_to_analyzing
                    first filtering
                    then analyzing;
                state analyzing;
            }
            
            transition monitoring_to_assessing
                first monitoring.analyzing
                then assessing;
            
            state assessing {
                entry; then evaluating;
                state evaluating;
                transition evaluating_to_prioritizing
                    first evaluating
                    then prioritizing;
                state prioritizing;
                transition prioritizing_to_reporting
                    first prioritizing
                    then reporting;
                state reporting;
            }
            
            transition assessing_to_monitoring
                first assessing.reporting
                then monitoring;
        }
        
        transition active_to_paused
            first active
            then paused;
        
        state paused;
        transition paused_to_active
            first paused
            then active;
        
        transition active_to_maintenance
            first active
            then maintenance;
        
        state maintenance;
        transition maintenance_to_ready
            first maintenance
            then ready;
    }
    
    part def TechnologyScoutingSystemDef {
        doc /* A Technology Scouting System is an intelligent platform that
             * automates the discovery, analysis, and prioritization of
             * emerging technologies across multiple domains. The system
             * employs continuous environmental scanning, multi-criteria
             * evaluation frameworks, and advanced analytics to transform
             * raw technology signals into actionable strategic intelligence
             * for innovation leaders and decision-makers. */
    }
    
    part technologyScoutingSystem : TechnologyScoutingSystemDef {
        doc /* Integrated platform that systematically discovers, analyzes,
             * and prioritizes emerging technologies to support strategic
             * innovation planning and competitive advantage. */
        
        attribute systemVersion : ScalarValues::String = "3.0.1";
        attribute operationalMode : ScalarValues::String;
        attribute scoutingDomains : ScalarValues::String[1..*];
        attribute updateFrequency : ISQ::DurationValue = 24.0 [SI::h];
        
        part collector : DataCollectionModule {
            attribute :>> monitoredSources = 35;
            attribute :>> collectionFrequency = 12.0 [SI::h];
            attribute :>> signalProcessingRate = 150.0;
        }
        
        part analyzer : AnalysisEngine {
            attribute :>> evaluationFramework = (
                "technical_feasibility",
                "market_readiness",
                "strategic_alignment",
                "competitive_advantage",
                "implementation_complexity",
                "cost_benefit_ratio"
            );
            attribute :>> benchmarkDatabase = "industry_standards_v2.3";
            attribute :>> analysisAlgorithm = "multi_criteria_decision_analysis";
        }
        
        part prioritizer : PrioritizationModule {
            attribute :>> priorityWeights = (0.25, 0.20, 0.20, 0.15, 0.10, 0.10);
            attribute :>> rankingThreshold = 7.5;
            attribute :>> maxPriorityItems = 12;
        }
        
        part reporter : ReportingModule {
            attribute :>> reportTemplate = "executive_summary_v4";
            attribute :>> visualizationFormat = "interactive_dashboard";
            attribute :>> distributionList = (
                "cto@organization.com",
                "innovation_team@organization.com",
                "strategy_office@organization.com"
            );
        }
        
        part repository : KnowledgeRepository {
            attribute :>> databaseCapacity = 10000;
            attribute :>> retentionPeriod = 730.0 [SI::d];
        }
        
        part stakeholderInterface : StakeholderInterface {
            attribute :>> dashboardUrl = "https://techscout.organization.com/dashboard";
            attribute :>> notificationChannels = ("email", "slack", "mobile_app");
            attribute :>> userAccessLevel = "executive";
        }
        
        connection collectorToAnalyzer connect
            collector.candidateOutput to analyzer.analysisInput;
        
        connection analyzerToRepository connect
            analyzer to repository.repositoryAccess;
        
        connection repositoryToPrioritizer connect
            repository to prioritizer;
        
        connection prioritizerToReporter connect
            prioritizer to reporter;
        
        connection reporterToStakeholder connect
            reporter.reportOutput to stakeholderInterface;
        
        perform action scoutingOperation : TechnologyScoutingCycle;
        
        exhibit state systemBehavior : ScoutingSystemStates;
    }
    
    requirement <'REQ-TS-001'> continuousMonitoringRequirement {
        doc /* The technology scouting system shall continuously monitor
             * at least 30 diverse information sources including patent
             * databases, research publications, industry reports, and
             * startup ecosystems to identify emerging technologies. */
        
        subject system : TechnologyScoutingSystemDef;
        
        require constraint {
            technologyScoutingSystem.collector.monitoredSources >= 30
        }
    }
    
    requirement <'REQ-TS-002'> multiCriteriaAssessmentRequirement {
        doc /* The system shall evaluate each technology candidate using
             * a multi-criteria assessment framework covering at least
             * five evaluation dimensions including technical feasibility,
             * market potential, and strategic alignment. */
        
        subject analyzer : AnalysisEngine;
        
        require constraint {
            technologyScoutingSystem.analyzer.evaluationFramework->size() >= 5
        }
    }
    
    requirement <'REQ-TS-003'> prioritizationRequirement {
        doc /* The system shall prioritize technology candidates based on
             * weighted scoring and present between 5 and 15 top-ranked
             * candidates in each scouting report. */
        
        subject prioritizer : PrioritizationModule;
        
        require constraint {
            technologyScoutingSystem.prioritizer.maxPriorityItems >= 5 and
            technologyScoutingSystem.prioritizer.maxPriorityItems <= 15
        }
    }
    
    requirement <'REQ-TS-004'> reportGenerationRequirement {
        doc /* The system shall generate comprehensive scouting reports
             * containing executive summaries, detailed candidate profiles,
             * trend analysis, and actionable recommendations within
             * 24 hours of completing the assessment cycle. */
        
        subject reporter : ReportingModule;
    }
    
    requirement <'REQ-TS-005'> knowledgeRetentionRequirement {
        doc /* The system shall maintain a knowledge repository storing
             * at least 5000 technology candidates with full assessment
             * history for a minimum retention period of 2 years to
             * support trend analysis and pattern recognition. */
        
        subject repository : KnowledgeRepository;
        
        require constraint {
            technologyScoutingSystem.repository.databaseCapacity >= 5000 and
            technologyScoutingSystem.repository.retentionPeriod >= 730.0 [SI::d]
        }
    }
    
    requirement <'REQ-TS-006'> updateFrequencyRequirement {
        doc /* The system shall execute complete scouting cycles at least
             * once every 24 hours to ensure timely identification of
             * emerging technology opportunities. */
        
        subject system : TechnologyScoutingSystemDef;
        
        require constraint {
            technologyScoutingSystem.updateFrequency <= 24.0 [SI::h]
        }
    }
    
    requirement <'REQ-TS-007'> stakeholderEngagementRequirement {
        doc /* The system shall provide an interactive stakeholder interface
             * with real-time dashboard access and multi-channel notification
             * capabilities to facilitate timely decision-making. */
        
        subject interface : StakeholderInterface;
        
        require constraint {
            technologyScoutingSystem.stakeholderInterface.notificationChannels->size() >= 2
        }
    }
    
    requirement <'REQ-TS-MISSION'> primaryMissionRequirement {
        doc /* The technology scouting system shall systematically identify,
             * evaluate, and prioritize emerging technologies from diverse
             * global sources to provide strategic intelligence that enables
             * proactive innovation planning, competitive positioning, and
             * informed technology investment decisions. */
        
        subject system : TechnologyScoutingSystemDef;
        
        assume constraint validOperationalState {
            technologyScoutingSystem.operationalMode == "active"
        }
        
        require continuousMonitoringRequirement;
        require multiCriteriaAssessmentRequirement;
        require prioritizationRequirement;
        require reportGenerationRequirement;
        require knowledgeRetentionRequirement;
        require updateFrequencyRequirement;
        require stakeholderEngagementRequirement;
    }
    
    satisfy primaryMissionRequirement by technologyScoutingSystem;
}

// --- Test harness (auto-generated) ---
package ExecutionHarness {
    private import ScalarValues::*;
    private import ISQ::*;
    private import SI::*;
    private import TechnologyScoutingSystem::*;

    part technologyScoutingSystem : DataCollectionModule {
        exhibit state sm : ScoutingSystemStates;
    }

    action orchestrator {
        attribute testMonitoringChannels : ScalarValues::String[*];
        action monitorProbe : MonitorInformationSources {
            in monitoringChannels = testMonitoringChannels;
            in monitoringParameters = "";
        }
        first monitorProbe;
    }
}

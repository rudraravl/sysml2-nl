package DevelopmentalRoboticsSystem {
    private import ScalarValues::*;
    private import ISQ::*;
    private import SI::*;
    
    attribute def SensorReading;
    attribute def MotorSignal;
    attribute def InternalRepresentation;
    
    value def SkillCompetence :> Real;
    value def PredictionAccuracy :> Real;
    value def ConfidenceScore :> Real;
    value def ExplorationFactor :> Real;
    value def LearningCoefficient :> Real;
    
    item def VisualPercept {
        attribute imageData : SensorReading;
        attribute objectFeatures : SensorReading[*];
        attribute spatialLocation : LengthValue[3];
        attribute captureTime : TimeValue;
    }
    
    item def ProprioceptiveState {
        attribute jointAngles : PlaneAngleValue[*];
        attribute jointVelocities : AngularVelocityValue[*];
        attribute jointTorques : TorqueValue[*];
        attribute timestamp : TimeValue;
    }
    
    item def TactileFeedback {
        attribute contactForces : ForceValue[*];
        attribute contactLocations : LengthValue[*];
        attribute surfaceTexture : SensorReading;
        attribute timestamp : TimeValue;
    }
    
    item def ActionCommand {
        attribute targetJointAngles : PlaneAngleValue[*];
        attribute targetVelocities : AngularVelocityValue[*];
        attribute gripperState : Real;
        attribute executionDuration : TimeValue;
    }
    
    item def SensorimotorExperience {
        attribute priorSensoryState : SensorReading;
        attribute executedAction : ActionCommand;
        attribute resultingSensoryState : SensorReading;
        attribute predictionError : Real;
        attribute timestamp : TimeValue;
    }
    
    item def WorldModel {
        attribute objectRepresentations : InternalRepresentation[*];
        attribute actionEffectPredictions : InternalRepresentation[*];
        attribute bodySchema : InternalRepresentation;
        attribute modelConfidence : ConfidenceScore;
    }
    
    port def VisionPort {
        in item visualInput : VisualPercept;
    }
    
    port def ProprioceptionPort {
        in item bodyState : ProprioceptiveState;
    }
    
    port def TactilePort {
        in item touchInput : TactileFeedback;
    }
    
    port def MotorPort {
        out item motorCommand : ActionCommand;
    }
    
    port def LearningDataPort {
        in item experience : SensorimotorExperience;
        out item updatedModel : WorldModel;
    }
    
    part def VisionSystem {
        port visionOut : ~VisionPort;
        attribute resolution : Integer;
        attribute frameRate : FrequencyValue;
        perform action captureVisualData;
    }
    
    part def ProprioceptiveSensors {
        port proprioOut : ~ProprioceptionPort;
        attribute sensorCount : Integer;
        attribute samplingRate : FrequencyValue;
        perform action measureBodyState;
    }
    
    part def TactileSensorArray {
        port tactileOut : ~TactilePort;
        attribute sensorDensity : Real;
        attribute sensitivity : ForceValue;
        perform action detectContact;
    }
    
    part def RoboticManipulator {
        port motorIn : MotorPort;
        attribute degreesOfFreedom : Integer;
        attribute maxReach : LengthValue;
        attribute payloadCapacity : MassValue;
        perform action executeMotion;
    }
    
    part def PredictiveEngine {
        port sensoryIn : VisionPort;
        port proprioIn : ProprioceptionPort;
        port tactileIn : TactilePort;
        port modelInterface : LearningDataPort;
        
        attribute currentWorldModel : WorldModel;
        attribute predictionHorizon : TimeValue;
        
        perform action integrateMultimodalSensing;
        perform action predictActionOutcome;
    }
    
    part def MotorPlanner {
        port modelIn : ~LearningDataPort;
        port motorOut : ~MotorPort;
        
        attribute explorationRate : ExplorationFactor;
        attribute planningDepth : Integer;
        
        perform action generateActionSequence;
        perform action balanceExplorationExploitation;
    }
    
    part def DevelopmentalLearningModule {
        port experienceIn : LearningDataPort;
        port modelOut : ~LearningDataPort;
        
        attribute learningRate : LearningCoefficient;
        attribute experienceMemory : SensorimotorExperience[*];
        attribute modelParameters : InternalRepresentation;
        
        perform action consolidateExperience;
        perform action refineWorldModel;
    }
    
    action def AcquireMultimodalSensation {
        in visualData : VisualPercept;
        in proprioData : ProprioceptiveState;
        in tactileData : TactileFeedback;
        out integratedPercept : SensorReading;
    }
    
    action def FormPrediction {
        in currentPercept : SensorReading;
        in candidateAction : ActionCommand;
        in worldModel : WorldModel;
        out predictedOutcome : SensorReading;
        out confidence : ConfidenceScore;
    }
    
    action def DecideAction {
        in currentPercept : SensorReading;
        in worldModel : WorldModel;
        in explorationFactor : ExplorationFactor;
        out selectedAction : ActionCommand;
        out isExploratory : Boolean;
    }
    
    action def ExecuteMotorAction {
        in actionCommand : ActionCommand;
        out motorSignals : MotorSignal;
    }
    
    action def EvaluatePrediction {
        in predictedOutcome : SensorReading;
        in actualOutcome : SensorReading;
        out error : Real;
        out surprise : Real;
    }
    
    action def LearnFromExperience {
        in predictionError : Real;
        in experience : SensorimotorExperience;
        in currentModel : WorldModel;
        in learningRate : LearningCoefficient;
        out refinedModel : WorldModel;
    }
    
    action def MeasureSkillCompetence {
        in recentErrors : Real[*];
        in modelConfidence : ConfidenceScore;
        out competenceLevel : SkillCompetence;
    }
    
    action def AdaptExplorationStrategy {
        in competenceLevel : SkillCompetence;
        in currentExploration : ExplorationFactor;
        out adjustedExploration : ExplorationFactor;
    }
    
    action def SensorimotorDevelopmentCycle {
        in initialWorldModel : WorldModel;
        in initialExploration : ExplorationFactor;
        in maxIterations : Integer;
        out matureWorldModel : WorldModel;
        out finalCompetence : SkillCompetence;
        
        private attribute evolvedModel := initialWorldModel;
        private attribute explorationParameter := initialExploration;
        private attribute previousPercept : SensorReading;
        private attribute errorHistory : Real[*] := ();
        private attribute iterationCount : Integer := 0;
        
        first start;
        then merge developmentLoop;
        
        then action sense : AcquireMultimodalSensation {
            in visualData;
            in proprioData;
            in tactileData;
            out integratedPercept;
        }
        
        then action predict : FormPrediction {
            in currentPercept = sense.integratedPercept;
            in candidateAction;
            in worldModel = evolvedModel;
            out predictedOutcome;
            out confidence;
        }
        
        then action decide : DecideAction {
            in currentPercept = sense.integratedPercept;
            in worldModel = evolvedModel;
            in explorationFactor = explorationParameter;
            out selectedAction;
            out isExploratory;
        }
        
        then action act : ExecuteMotorAction {
            in actionCommand = decide.selectedAction;
            out motorSignals;
        }
        
        then action senseAgain : AcquireMultimodalSensation {
            in visualData;
            in proprioData;
            in tactileData;
            out integratedPercept;
        }
        
        then action evaluate : EvaluatePrediction {
            in predictedOutcome = predict.predictedOutcome;
            in actualOutcome = senseAgain.integratedPercept;
            out error;
            out surprise;
        }
        
        then action learn : LearnFromExperience {
            in predictionError = evaluate.error;
            in experience;
            in currentModel = evolvedModel;
            in learningRate;
            out refinedModel;
        }
        
        then assign evolvedModel := learn.refinedModel;
        then assign previousPercept := senseAgain.integratedPercept;
        then assign errorHistory := errorHistory->including(evaluate.error);
        then assign iterationCount := iterationCount + 1;
        
        then action measure : MeasureSkillCompetence {
            in recentErrors = errorHistory;
            in modelConfidence = predict.confidence;
            out competenceLevel;
        }
        
        then action adapt : AdaptExplorationStrategy {
            in competenceLevel = measure.competenceLevel;
            in currentExploration = explorationParameter;
            out adjustedExploration;
        }
        
        then assign explorationParameter := adapt.adjustedExploration;
        
        then decide;
            if iterationCount < maxIterations and measure.competenceLevel < 0.95 then developmentLoop;
            if iterationCount >= maxIterations or measure.competenceLevel >= 0.95 then complete;
        
        action complete {
            assign matureWorldModel := evolvedModel;
            assign finalCompetence := measure.competenceLevel;
        }
        then done;
    }
    
    state def DevelopmentalPhases {
        entry; then reflexive;
        
        state reflexive {
            doc /* Initial phase: random motor babbling and basic sensory exploration */
            entry assign explorationRate := 0.9;
            do action randomExploration {
                out randomActions : ActionCommand[*];
            }
        }
        then [competence > 0.2] coordinative;
        
        state coordinative {
            doc /* Intermediate phase: coordinated sensorimotor patterns emerge */
            entry assign explorationRate := 0.6;
            do action practiceCoordination {
                in patterns : InternalRepresentation[*];
                out refinedPatterns : InternalRepresentation[*];
            }
        }
        then [competence > 0.5] goalDirected;
        
        state goalDirected {
            doc /* Advanced phase: purposeful actions toward specific outcomes */
            entry assign explorationRate := 0.3;
            do action pursueGoals {
                in desiredOutcome : SensorReading;
                in worldModel : WorldModel;
                out actionPlan : ActionCommand[*];
            }
        }
        then [competence > 0.8] skilled;
        
        state skilled {
            doc /* Mature phase: efficient, adaptive skilled behavior */
            entry assign explorationRate := 0.1;
            do action executeSkills {
                in complexGoal : SensorReading;
                out optimizedActions : ActionCommand[*];
            }
        }
    }
    
    part developmentalRobot {
        doc /* Autonomous developmental robotics system that learns sensorimotor skills through self-exploration */
        
        part vision : VisionSystem;
        part proprioception : ProprioceptiveSensors;
        part tactile : TactileSensorArray;
        part manipulator : RoboticManipulator;
        part predictor : PredictiveEngine;
        part planner : MotorPlanner;
        part learner : DevelopmentalLearningModule;
        
        connect vision.visionOut to predictor.sensoryIn;
        connect proprioception.proprioOut to predictor.proprioIn;
        connect tactile.tactileOut to predictor.tactileIn;
        connect predictor.modelInterface to learner.experienceIn;
        connect learner.modelOut to planner.modelIn;
        connect planner.motorOut to manipulator.motorIn;
        
        perform action developSkills : SensorimotorDevelopmentCycle {
            in initialWorldModel;
            in initialExploration;
            in maxIterations;
            out matureWorldModel;
            out finalCompetence;
        }
        
        perform developSkills.sense by vision;
        perform developSkills.predict by predictor;
        perform developSkills.decide by planner;
        perform developSkills.act by manipulator;
        perform developSkills.learn by learner;
        
        exhibit state developmentalProgress : DevelopmentalPhases;
    }
    
    requirement def AutonomousSkillAcquisition {
        doc /* The system shall autonomously acquire sensorimotor skills through self-directed exploration and interaction with the environment without explicit programming of behaviors. */
        
        require constraint {
            developmentalRobot.learner.learningRate > 0.0
        }
    }
    
    requirement def PredictiveModelDevelopment {
        doc /* The system shall develop internal predictive models of sensorimotor contingencies that enable anticipation of action outcomes. */
        
        require constraint {
            developmentalRobot.predictor.currentWorldModel.modelConfidence > 0.6
        }
    }
    
    requirement def ProgressiveDevelopment {
        doc /* The system shall progress through developmental phases from reflexive exploration to skilled goal-directed behavior. */
        
        require constraint {
            developmentalRobot.developSkills.finalCompetence >= 0.0
        }
    }
    
    requirement def MultimodalIntegration {
        doc /* The system shall integrate visual, proprioceptive, and tactile sensory modalities to form coherent perceptual representations. */
        
        require constraint {
            developmentalRobot.vision.frameRate > 0.0[Hz] and
            developmentalRobot.proprioception.samplingRate > 0.0[Hz] and
            developmentalRobot.tactile.sensorDensity > 0.0
        }
    }
    
    requirement <'DR-SYS-001'> developmentalRoboticsSystemRequirement {
        doc /* The developmental robotics system shall enable a robot to autonomously develop sensorimotor competencies through progressive learning phases that mirror biological development, using predictive models of action-perception contingencies to guide skill acquisition from reflexive exploration to purposeful goal-directed behavior. */
        
        subject developmentalRobot;
        
        assume constraint environmentRichness {
            doc /* The robot operates in a sufficiently complex and interactive environment that provides diverse sensorimotor experiences. */
        }
        
        assume constraint embodimentSuitability {
            doc /* The robot's physical embodiment provides adequate sensory and motor capabilities for developmental learning. */
            developmentalRobot.manipulator.degreesOfFreedom >= 3
        }
        
        require autonomousAcquisition : AutonomousSkillAcquisition;
        require predictiveModeling : PredictiveModelDevelopment;
        require progressiveLearning : ProgressiveDevelopment;
        require multimodalSensing : MultimodalIntegration;
        
        require constraint learningConvergence {
            doc /* The developmental learning process shall converge toward stable sensorimotor competencies over time. */
            developmentalRobot.developSkills.finalCompetence > 0.7
        }
        
        require constraint explorationAdaptation {
            doc /* The exploration strategy shall adapt based on acquired competence, decreasing exploration as skills mature. */
            developmentalRobot.planner.explorationRate >= 0.0 and
            developmentalRobot.planner.explorationRate <= 1.0
        }
    }
}

// --- Test harness (auto-generated) ---
package ExecutionHarness {
    private import ScalarValues::*;
    private import ISQ::*;
    private import SI::*;
    private import DevelopmentalRoboticsSystem::*;

    part testSubject = developmentalRobot {
        exhibit state sm : DevelopmentalPhases;
    }

    action orchestrator {
        action actionProbe : AcquireMultimodalSensation {
            // TODO(human): unsupported input type for visualData: VisualPercept (unsupported structured payload members: objectFeatures, spatialLocation)
            // TODO(human): unsupported input type for proprioData: ProprioceptiveState (unsupported structured payload members: jointAngles, jointVelocities, jointTorques)
            // TODO(human): unsupported input type for tactileData: TactileFeedback (unsupported structured payload members: contactForces, contactLocations)
        }
        first actionProbe;
    }
}

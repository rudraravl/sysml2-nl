package 'Adaptive Deep Brain Stimulation System' {
    private import ScalarValues::*;
    private import ISQ::*;
    private import SI::*;

    attribute def NeuralOscillationAmplitude :> Real {
        doc /* Amplitude of neural oscillatory activity measured in microvolts */
    }

    attribute def StimulationCurrent :> Real {
        doc /* Therapeutic electrical current delivered in milliamperes */
    }

    attribute def PulseFrequency :> Real {
        doc /* Frequency of stimulation pulses in Hertz */
    }

    attribute def PulseWidthDuration :> Real {
        doc /* Duration of individual stimulation pulse in microseconds */
    }

    attribute def PathologyThreshold :> Real {
        doc /* Neural activity threshold indicating pathological state */
    }

    attribute def BiomarkerLevel :> Real {
        doc /* Quantified level of pathological neural biomarker */
    }

    attribute def SystemCommand;
    attribute def TherapyStart;
    attribute def TherapyStop;
    attribute def ConfigurationUpdate;

    port def NeuralSensingPort {
        out neuralSignal : NeuralOscillationAmplitude;
        out impedance : Real;
    }

    port def StimulationDeliveryPort {
        in current : StimulationCurrent;
        in frequency : PulseFrequency;
        in pulseWidth : PulseWidthDuration;
    }

    port def ControlInterfacePort {
        in threshold : PathologyThreshold;
        in targetParameters : SystemCommand;
        out currentState : BiomarkerLevel;
    }

    port def PowerPort {
        out voltage : ElectricPotentialValue;
        out current : ElectricCurrentValue;
    }

    port def TelemetryPort {
        out diagnosticData : Real;
        in programmingData : Real;
    }

    part def SensingElectrode {
        doc /* Implanted electrode array for recording neural field potentials from target brain region */
        port neuralOutput : NeuralSensingPort;
        
        attribute electrodeCount : Integer;
        attribute contactSurfaceArea : AreaValue;
    }

    part def BiomarkerExtractor {
        doc /* Digital signal processor extracting pathological biomarkers from raw neural signals */
        port rawSignalInput : ~NeuralSensingPort;
        port biomarkerOutput : ~NeuralSensingPort;
        
        attribute samplingRate : FrequencyValue;
        attribute filterBandwidth : FrequencyValue;
        
        action extractBiomarker {
            in rawAmplitude : NeuralOscillationAmplitude;
            out betaBandPower : BiomarkerLevel;
            out gammaActivity : BiomarkerLevel;
        }
    }

    part def ClosedLoopController {
        doc /* Adaptive controller computing optimal stimulation parameters based on neural state */
        port biomarkerInput : ~NeuralSensingPort;
        port controlInterface : ControlInterfacePort;
        port stimulationCommand : ~StimulationDeliveryPort;
        
        attribute adaptiveGain : Real;
        attribute updateRate : FrequencyValue;
        attribute currentThreshold : PathologyThreshold;
        
        action computeTherapy {
            in biomarker : BiomarkerLevel;
            in threshold : PathologyThreshold;
            out stimCurrent : StimulationCurrent;
            out stimFrequency : PulseFrequency;
            out stimPulseWidth : PulseWidthDuration;
        }
        
        action adaptThreshold {
            in historicalBiomarker : BiomarkerLevel;
            out updatedThreshold : PathologyThreshold;
        }
    }

    part def PulseGenerator {
        doc /* Programmable waveform generator producing therapeutic electrical pulses */
        port commandInput : ~StimulationDeliveryPort;
        port pulseOutput : StimulationDeliveryPort;
        
        attribute maxCurrent : ElectricCurrentValue;
        attribute minPulseWidth : TimeValue;
        attribute maxFrequency : FrequencyValue;
        
        action generatePulse {
            in amplitude : StimulationCurrent;
            in frequency : PulseFrequency;
            in width : PulseWidthDuration;
            out electricalPulse : SystemCommand;
        }
    }

    part def StimulationElectrode {
        doc /* Implanted electrode delivering therapeutic electrical stimulation to target tissue */
        port stimulationInput : StimulationDeliveryPort;
        
        attribute electrodeCount : Integer;
        attribute contactConfiguration : String;
    }

    part def ImplantableBattery {
        doc /* Rechargeable power source for all implanted components */
        port powerOutput : PowerPort;
        
        attribute capacity : EnergyValue;
        attribute remainingCharge : EnergyValue;
        attribute voltage : ElectricPotentialValue;
        
        action monitorCharge {
            out chargeLevel : Real;
            out estimatedLifetime : TimeValue;
        }
    }

    part def WirelessTelemetry {
        doc /* Bidirectional wireless communication for programming and data retrieval */
        port telemetryInterface : TelemetryPort;
        
        attribute communicationFrequency : FrequencyValue;
        attribute dataRate : Real;
        
        action transmitDiagnostics {
            in neuralData : BiomarkerLevel;
            in stimulationData : StimulationCurrent;
            in batteryStatus : Real;
        }
        
        action receiveConfiguration {
            out newThreshold : PathologyThreshold;
            out newParameters : SystemCommand;
        }
    }

    part def AdaptiveDBSSystem {
        doc /* Intelligent neurostimulation platform providing personalized, responsive therapy for movement disorders 
               and neuropsychiatric conditions through real-time neural feedback and adaptive parameter optimization */
        
        part sensingElectrode : SensingElectrode;
        part biomarkerExtractor : BiomarkerExtractor;
        part controller : ClosedLoopController;
        part pulseGenerator : PulseGenerator;
        part stimulationElectrode : StimulationElectrode;
        part battery : ImplantableBattery;
        part telemetry : WirelessTelemetry;
    }

    requirement def PrimaryTherapeuticRequirement {
        doc /* System shall suppress pathological neural oscillations while preserving normal brain function */
        subject system : AdaptiveDBSSystem;
        require constraint {
            system.biomarkerExtractor.biomarkerOutput.neuralSignal < system.controller.currentThreshold
        }
    }

    requirement def AdaptationLatencyRequirement {
        doc /* System shall detect pathological activity and adjust stimulation within 200 milliseconds */
        subject system : AdaptiveDBSSystem;
    }

    requirement def BatteryEnduranceRequirement {
        doc /* System shall operate continuously for minimum 7 years without battery replacement */
        subject system : AdaptiveDBSSystem;
        require constraint {
            system.battery.remainingCharge > 0.0
        }
    }

    requirement def StimulationSafetyRequirement {
        doc /* Stimulation current shall not exceed safe tissue charge density limits */
        subject system : AdaptiveDBSSystem;
        require constraint {
            system.stimulationElectrode.stimulationInput.current <= 15.0 and
            system.stimulationElectrode.stimulationInput.current >= 0.0
        }
    }

    requirement def BiocompatibilityRequirement {
        doc /* All implanted materials shall meet ISO 10993 biocompatibility standards */
        subject system : AdaptiveDBSSystem;
    }

    action def SenseNeuralActivity {
        in electrode : SensingElectrode;
        out rawSignal : NeuralOscillationAmplitude;
    }

    action def ExtractPathologyBiomarker {
        in rawSignal : NeuralOscillationAmplitude;
        out biomarkerValue : BiomarkerLevel;
    }

    action def AssessPathologicalState {
        in biomarker : BiomarkerLevel;
        in threshold : PathologyThreshold;
        out isPathological : Boolean;
        out severityLevel : Real;
    }

    action def DetermineStimulationDose {
        in severityLevel : Real;
        in previousCurrent : StimulationCurrent;
        out targetCurrent : StimulationCurrent;
        out targetFrequency : PulseFrequency;
        out targetPulseWidth : PulseWidthDuration;
    }

    action def ApplyTherapeuticStimulation {
        in current : StimulationCurrent;
        in frequency : PulseFrequency;
        in pulseWidth : PulseWidthDuration;
    }

    action def RefineTherapyThreshold {
        in recentBiomarkers : BiomarkerLevel[*];
        in therapeuticOutcome : Real;
        out optimizedThreshold : PathologyThreshold;
    }

    action def MonitorSystemHealth {
        in batteryLevel : Real;
        in electrodeImpedance : Real;
        out systemStatus : Boolean;
    }

    action adaptiveTherapyControl {
        doc /* Continuous closed-loop therapeutic action: sense pathological activity and deliver adaptive stimulation */
        
        first start;
        then merge continuousTherapy;
        
        then action sense : SenseNeuralActivity {
            in electrode;
            out rawSignal : NeuralOscillationAmplitude;
        }
        
        then action extract : ExtractPathologyBiomarker {
            in rawSignal = sense.rawSignal;
            out biomarkerValue : BiomarkerLevel;
        }
        
        then action assess : AssessPathologicalState {
            in biomarker = extract.biomarkerValue;
            in threshold : PathologyThreshold;
            out isPathological : Boolean;
            out severityLevel : Real;
        }
        
        then decide;
            if assess.isPathological then escalateTherapy;
            if not assess.isPathological then maintainBaseline;
        
        action escalateTherapy : DetermineStimulationDose {
            in severityLevel = assess.severityLevel;
            in previousCurrent : StimulationCurrent;
            out targetCurrent : StimulationCurrent;
            out targetFrequency : PulseFrequency;
            out targetPulseWidth : PulseWidthDuration;
        }
        then deliverStimulation;
        
        action maintainBaseline : DetermineStimulationDose {
            in severityLevel = assess.severityLevel;
            in previousCurrent : StimulationCurrent;
            out targetCurrent : StimulationCurrent;
            out targetFrequency : PulseFrequency;
            out targetPulseWidth : PulseWidthDuration;
        }
        then deliverStimulation;
        
        action deliverStimulation : ApplyTherapeuticStimulation {
            in current = escalateTherapy.targetCurrent;
            in frequency = escalateTherapy.targetFrequency;
            in pulseWidth = escalateTherapy.targetPulseWidth;
        }
        
        then action refine : RefineTherapyThreshold {
            in recentBiomarkers : BiomarkerLevel[*];
            in therapeuticOutcome : Real;
            out optimizedThreshold : PathologyThreshold;
        }
        
        then action monitor : MonitorSystemHealth {
            in batteryLevel : Real;
            in electrodeImpedance : Real;
            out systemStatus : Boolean;
        }
        
        then continuousTherapy;
    }

    part adaptiveDBSSystem : AdaptiveDBSSystem {
        doc /* Fully implantable closed-loop neurostimulation system that continuously monitors pathological brain activity 
               and automatically adjusts therapeutic electrical stimulation in real-time to suppress symptoms while 
               minimizing side effects and power consumption */
        
        part sensingElectrode : SensingElectrode {
            :>> electrodeCount = 4;
        }
        
        part biomarkerExtractor : BiomarkerExtractor;
        
        part controller : ClosedLoopController {
            :>> adaptiveGain = 0.5;
        }
        
        part pulseGenerator : PulseGenerator;
        
        part stimulationElectrode : StimulationElectrode {
            :>> electrodeCount = 4;
            :>> contactConfiguration = "directional";
        }
        
        part battery : ImplantableBattery;
        
        part telemetry : WirelessTelemetry;
        
        connect sensingElectrode.neuralOutput to biomarkerExtractor.rawSignalInput;
        connect biomarkerExtractor.biomarkerOutput to controller.biomarkerInput;
        connect controller.stimulationCommand to pulseGenerator.commandInput;
        connect pulseGenerator.pulseOutput to stimulationElectrode.stimulationInput;
        
        perform action therapy : adaptiveTherapyControl;
    }
}

// --- Test harness (auto-generated) ---
package ExecutionHarness {
    private import ScalarValues::*;
    private import ISQ::*;
    private import SI::*;
    private import 'Adaptive Deep Brain Stimulation System'::*;

    action orchestrator {
        attribute testPreviousCurrent : StimulationCurrent = 0.0;
        action escalateTherapyProbe : DetermineStimulationDose {
            in severityLevel = 0.0;
            in previousCurrent = testPreviousCurrent;
        }
        first escalateTherapyProbe;
    }
}

package 'Messaging Example' {
	item def Scene;
	item def Image;
	item def Picture;
	
	attribute def Show {
		item picture : Picture;
	}
	
	action def Focus { in item scene : Scene; out item image : Image; }
	action def Shoot { in item image : Image; out item picture : Picture; }
	action def TakePicture;
	
	action screen;
		
	action takePicture : TakePicture {
		action trigger accept scene : Scene;
		
		then action focus : Focus {
			in item scene = trigger.scene;
			out item image;
		}
		
		flow from focus.image to shoot.image;
		
		then action shoot : Shoot {
			in item image; 
			out item picture;
		}
		
		then send new Show(shoot.picture) to screen;
	}
}

// --- Test harness (auto-generated) ---
package ExecutionHarness {
    private import 'Messaging Example'::*;

    action orchestrator {
        item testScene : Scene;
        action takePictureProbe : TakePicture {
        }
        action triggerScene send testScene to takePictureProbe;
        first takePictureProbe;
        then triggerScene;
    }
}

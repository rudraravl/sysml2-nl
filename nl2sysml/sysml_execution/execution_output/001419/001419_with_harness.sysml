package EphemeralizationSystem {
    private import ScalarValues::*;
    private import ISQ::*;
    private import SI::*;
    
    attribute def EfficiencyMetric :> Real;
    attribute def ResourceIntensity :> Real;
    attribute def OutputCapability :> Real;
    attribute def GenerationNumber :> Integer;
    
    attribute def PerformanceRatio {
        attribute outputPerMass :> Real;
        attribute outputPerEnergy :> Real;
        attribute outputPerTime :> Real;
    }
    
    item def PhysicalResource {
        attribute mass :> ISQ::mass;
        attribute energyContent :> ISQ::energy;
    }
    
    item def ServiceOutput {
        attribute capacity :> OutputCapability;
        attribute quality :> Real;
    }
    
    port def ResourceInputPort {
        in item materialInput : PhysicalResource;
        in attribute energyInput :> ISQ::power;
    }
    
    port def ServiceOutputPort {
        out item serviceDelivered : ServiceOutput;
        out attribute performanceMetric : PerformanceRatio;
    }
    
    part def ResourceMinimizer {
        port resourceIn : ResourceInputPort;
        attribute currentEfficiency :> EfficiencyMetric;
        attribute targetEfficiency :> EfficiencyMetric;
        
        perform action minimizeResources {
            in materialUsage :> ISQ::mass;
            in energyUsage :> ISQ::power;
            out optimizedMaterial :> ISQ::mass;
            out optimizedEnergy :> ISQ::power;
            out efficiencyGain :> EfficiencyMetric;
        }
    }
    
    part def CapabilityMaximizer {
        port serviceOut : ServiceOutputPort;
        attribute amplificationFactor :> Real;
        
        perform action maximizeOutput {
            in baseCapability :> OutputCapability;
            in availableResources :> ResourceIntensity;
            out enhancedCapability :> OutputCapability;
            out performanceRatio :> PerformanceRatio;
        }
    }
    
    part def TechnologyEvolver {
        attribute generation :> GenerationNumber;
        attribute innovationRate :> Real;
        
        perform action evolve {
            in currentGen :> GenerationNumber;
            in performanceTarget : PerformanceRatio;
            out nextGen :> GenerationNumber;
            out capabilityIncrease :> Real;
            out resourceDecrease :> Real;
        }
    }
    
    requirement def EphemeralizationPrinciple {
        doc /* The system shall embody ephemeralization by continuously achieving 
             greater functional output with progressively fewer physical resources, 
             demonstrating technological advancement through dematerialization. */
        
        require constraint doMoreWithLess {
            attribute resourceReduction :> Real;
            attribute capabilityGrowth :> Real;
            capabilityGrowth > 0.0 and resourceReduction > 0.0
        }
    }
    
    requirement def EfficiencyImprovement {
        doc /* Each successive generation shall demonstrate measurable improvement 
             in resource efficiency compared to the previous generation. */
        
        attribute minImprovementFactor :> EfficiencyMetric = 1.25;
        
        require constraint generationalGain {
            attribute newEfficiency :> EfficiencyMetric;
            attribute oldEfficiency :> EfficiencyMetric;
            newEfficiency >= oldEfficiency * minImprovementFactor
        }
    }
    
    requirement def OutputScalability {
        doc /* The system shall scale output capability without proportional 
             increase in material mass or energy consumption. */
        
        require constraint sublinearScaling {
            attribute outputGrowth :> Real;
            attribute resourceGrowth :> Real;
            resourceGrowth < outputGrowth
        }
    }
    
    action def MonitorPerformance {
        in currentMetrics : PerformanceRatio;
        in historicalData : PerformanceRatio[*];
        out trend :> Real;
        out projectedGain :> Real;
    }
    
    action def AdjustStrategy {
        in performanceTrend :> Real;
        in targetMetrics : PerformanceRatio;
        out strategyParameters :> Real[*];
    }
    
    action def EphemeralizationProcess {
        first start;
        then merge continuousOptimization;
        
        then action monitor : MonitorPerformance {
            in currentMetrics;
            in historicalData;
            out trend;
            out projectedGain;
        }
        
        then decide;
            if monitor.trend >= 0.0 then maintainCourse;
            if monitor.trend < 0.0 then adjustCourse;
        
        action maintainCourse {
            then action evolve : TechnologyEvolver::evolve;
        }
        then continuousOptimization;
        
        action adjustCourse : AdjustStrategy {
            in performanceTrend = monitor.trend;
            in targetMetrics;
            out strategyParameters;
        }
        then action reoptimize : ResourceMinimizer::minimizeResources;
        then continuousOptimization;
    }
    
    state def EvolutionaryStates {
        entry; then initialState;
        
        state initialState;
        then optimizing;
        
        state optimizing {
            do action optimize : ResourceMinimizer::minimizeResources;
        }
        then [optimize.efficiencyGain >= 0.15] advancing;
        then [optimize.efficiencyGain < 0.15] optimizing;
        
        state advancing {
            do action advance : TechnologyEvolver::evolve;
        }
        then expanding;
        
        state expanding {
            do action expand : CapabilityMaximizer::maximizeOutput;
        }
        then optimizing;
        
        state mature {
            do action maintain : MonitorPerformance;
        }
    }
    
    part ephemeralizationSystem {
        doc /* A system demonstrating ephemeralization: the principle of achieving 
             progressively greater functional capability with progressively less 
             material resources, energy, and time through continuous technological 
             evolution and intelligent optimization. This represents the fundamental 
             trend of doing more with less. */
        
        satisfy EphemeralizationPrinciple by self;
        satisfy EfficiencyImprovement by self;
        satisfy OutputScalability by self;
        
        part minimizer : ResourceMinimizer {
            :>> currentEfficiency = 1.0;
            :>> targetEfficiency = 2.5;
        }
        
        part maximizer : CapabilityMaximizer {
            :>> amplificationFactor = 1.8;
        }
        
        part evolver : TechnologyEvolver {
            :>> generation = 1;
            :>> innovationRate = 0.2;
        }
        
        connection resourceOptimization connect 
            minimizer.resourceIn to evolver;
        
        connection capabilityEnhancement connect 
            evolver to maximizer.serviceOut;
        
        perform action ephemeralizeOperation : EphemeralizationProcess;
        
        exhibit state evolutionCycle : EvolutionaryStates;
    }
}

// --- Test harness (auto-generated) ---
package ExecutionHarness {
    private import ScalarValues::*;
    private import ISQ::*;
    private import SI::*;
    private import EphemeralizationSystem::*;

    part testSubject = ephemeralizationSystem {
        exhibit state sm : EvolutionaryStates;
    }

    action orchestrator {
        action adjustCourseProbe : AdjustStrategy {
            // TODO(human): unsupported input type for performanceTrend: > Real (type is not a primitive, enum, extracted payload def, or known value type)
            // TODO(human): unsupported input type for targetMetrics: PerformanceRatio (unsupported structured payload members: outputPerMass, outputPerEnergy, outputPerTime)
        }
        first adjustCourseProbe;
    }
}

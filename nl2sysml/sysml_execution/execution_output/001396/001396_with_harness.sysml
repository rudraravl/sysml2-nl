package 'Design Automation and Test in Europe System' {
	private import ScalarValues::*;
	private import ISQ::*;
	private import SI::*;
	private import Time::*;
	private import NumericalFunctions::*;

	attribute def DesignID;
	attribute def TestID;
	attribute def CoveragePercentage :> Real;

	item def HDLSpecification {
		attribute designID : DesignID;
		attribute description : String;
		attribute targetTechnology : String;
		attribute clockFrequency : FrequencyValue;
	}

	item def SynthesizedNetlist {
		attribute designID : DesignID;
		attribute gateCount : Integer;
		attribute criticalPathDelay : TimeValue;
		attribute powerEstimate : PowerValue;
	}

	item def TestPattern {
		attribute testID : TestID;
		attribute vectorCount : Integer;
		attribute faultCoverage : CoveragePercentage;
	}

	item def TestResult {
		attribute testID : TestID;
		attribute passed : Boolean;
		attribute detectedFaults : Integer;
		attribute actualCoverage : CoveragePercentage;
	}

	item def VerificationReport {
		attribute designID : DesignID;
		attribute functionalCorrectness : Boolean;
		attribute timingMet : Boolean;
		attribute coverageAchieved : CoveragePercentage;
	}

	port def DesignInputPort {
		in item specification : HDLSpecification;
	}

	port def SynthesisOutputPort {
		out item netlist : SynthesizedNetlist;
	}

	port def TestPatternPort {
		out item patterns : TestPattern;
	}

	port def TestResultPort {
		in item results : TestResult;
	}

	part def LogicSynthesizer {
		attribute synthesisTime : DurationValue;
		attribute optimizationLevel : Integer;
		in port designIn : DesignInputPort;
		out port netlistOut : SynthesisOutputPort;

		action def SynthesizeDesign {
			in spec : HDLSpecification;
			out netlist : SynthesizedNetlist;
		}
	}

	part def FormalVerifier {
		attribute verificationDepth : Integer;
		attribute propertiesChecked : Integer;

		action def VerifyEquivalence {
			in spec : HDLSpecification;
			in netlist : SynthesizedNetlist;
			out isEquivalent : Boolean;
		}
	}

	part def TestPatternGenerator {
		attribute algorithmType : String;
		attribute targetCoverage : CoveragePercentage;
		out port patternOut : TestPatternPort;

		action def GeneratePatterns {
			in netlist : SynthesizedNetlist;
			out patterns : TestPattern;
		}
	}

	part def AutomaticTestEquipment {
		attribute maxFrequency : FrequencyValue;
		attribute channelCount : Integer;
		in port patternIn : TestPatternPort;
		out port resultOut : TestResultPort;

		action def ExecuteTest {
			in patterns : TestPattern;
			in dut : SynthesizedNetlist;
			out results : TestResult;
		}
	}

	part def DiagnosticAnalyzer {
		attribute faultDictionary : Integer;

		action def AnalyzeFailures {
			in results : TestResult;
			out faultLocations : String[0..*];
		}
	}

	part def ReportGenerator {
		action def CreateReport {
			in verificationStatus : Boolean;
			in testResults : TestResult;
			out report : VerificationReport;
		}
	}

	action def AutomatedDesignFlow {
		doc /* 
		Orchestrates the complete design automation and test flow from HDL specification
		through synthesis, verification, test pattern generation, and hardware testing.
		*/
		in specification : HDLSpecification;
		out finalReport : VerificationReport;

		first start;
		then action synthesize : LogicSynthesizer::SynthesizeDesign {
			in spec = specification;
		}
		then action verify : FormalVerifier::VerifyEquivalence {
			in spec = specification;
			in netlist = synthesize.netlist;
		}
		then decide;
			if verify.isEquivalent then generateTests;
			else reportFailure;

		action generateTests : TestPatternGenerator::GeneratePatterns {
			in netlist = synthesize.netlist;
		}
		then action executeTests : AutomaticTestEquipment::ExecuteTest {
			in patterns = generateTests.patterns;
			in dut = synthesize.netlist;
		}
		then decide;
			if executeTests.results.passed then reportSuccess;
			else diagnose;

		action diagnose : DiagnosticAnalyzer::AnalyzeFailures {
			in results = executeTests.results;
		}
		then reportFailure;

		merge reportFailure;
		action reportFailure : ReportGenerator::CreateReport {
			in verificationStatus = false;
			in testResults : TestResult;
		}
		then done;

		action reportSuccess : ReportGenerator::CreateReport {
			in verificationStatus = true;
			in testResults = executeTests.results;
		}
		then done;
	}

	state def DesignFlowLifecycle {
		entry; then idle;

		state idle;
		transition idle_to_synthesis
			first idle
			accept at specificationReceived
			then synthesis;

		state synthesis {
			entry; then synthesizing;
			state synthesizing;
		}
		transition synthesis_to_verification
			first synthesis
			accept at synthesisComplete
			then verification;

		state verification {
			entry; then verifying;
			state verifying;
			transition verifying_to_passed
				first verifying
				accept when equivalenceProven
				then passed;
			transition verifying_to_failed
				first verifying
				accept when equivalenceFailed
				then failed;
			state passed;
			state failed;
		}
		transition verification_to_testing
			first verification.passed
			then testing;

		state testing {
			entry; then patternGeneration;
			state patternGeneration;
			transition patternGeneration_to_execution
				first patternGeneration
				accept at patternsReady
				then execution;
			state execution;
			transition execution_to_analysis
				first execution
				accept at testComplete
				then analysis;
			state analysis;
		}
		transition testing_to_complete
			first testing
			then complete;
		transition verification_to_complete
			first verification.failed
			then complete;

		state complete;
	}

	requirement def SynthesisPerformanceRequirement {
		doc /* The synthesis process shall complete within acceptable time bounds. */
		subject synthesizer : LogicSynthesizer;
		in maxSynthesisTime : DurationValue;
		require constraint {
			synthesizer.synthesisTime <= maxSynthesisTime
		}
	}

	requirement def TestCoverageRequirement {
		doc /* The test pattern generation shall achieve minimum fault coverage. */
		subject generator : TestPatternGenerator;
		in minCoverage : CoveragePercentage;
		require constraint {
			generator.targetCoverage >= minCoverage
		}
	}

	requirement def VerificationCompletenessRequirement {
		doc /* The verification process shall check all critical design properties. */
		subject verifier : FormalVerifier;
		in minProperties : Integer;
		require constraint {
			verifier.propertiesChecked >= minProperties
		}
	}

	part def DATESystem {
		attribute systemName : String;
		attribute version : String;
		attribute maxDesignComplexity : Integer;

		part synthesizer : LogicSynthesizer;
		part verifier : FormalVerifier;
		part patternGen : TestPatternGenerator;
		part ate : AutomaticTestEquipment;
		part analyzer : DiagnosticAnalyzer;
		part reporter : ReportGenerator;
	}

	part dateSystem : DATESystem {
		doc /* 
		The Design Automation and Test in Europe (DATE) System provides an integrated
		platform for automated electronic design synthesis, formal verification, and
		comprehensive hardware testing. The system accepts high-level HDL specifications
		and produces verified, tested netlists with detailed quality reports, ensuring
		design correctness and manufacturability through rigorous automated validation.
		*/

		attribute :>> systemName = "DATE Integrated Design Platform";
		attribute :>> version = "2.0";
		attribute :>> maxDesignComplexity = 1000000;

		part :>> synthesizer {
			attribute :>> synthesisTime = 3600 [s];
			attribute :>> optimizationLevel = 3;
		}

		part :>> verifier {
			attribute :>> verificationDepth = 100;
			attribute :>> propertiesChecked = 50;
		}

		part :>> patternGen {
			attribute :>> algorithmType = "ATPG";
			attribute :>> targetCoverage = 98.5;
		}

		part :>> ate {
			attribute :>> maxFrequency = 1000 [MHz];
			attribute :>> channelCount = 512;
		}

		part :>> analyzer {
			attribute :>> faultDictionary = 10000;
		}

		connection synthToVerify connect 
			synthesizer.netlistOut to verifier;

		connection synthToPatternGen connect 
			synthesizer.netlistOut to patternGen;

		connection patternToATE connect 
			patternGen.patternOut to ate.patternIn;

		connection ateToAnalyzer connect 
			ate.resultOut to analyzer;

		perform action designFlow : AutomatedDesignFlow;

		assert requirement synthPerf : SynthesisPerformanceRequirement {
			subject synthesizer = dateSystem.synthesizer;
			in maxSynthesisTime = 7200 [s];
		}

		assert requirement testCov : TestCoverageRequirement {
			subject generator = dateSystem.patternGen;
			in minCoverage = 95.0;
		}

		assert requirement verifComplete : VerificationCompletenessRequirement {
			subject verifier = dateSystem.verifier;
			in minProperties = 40;
		}
	}

	occurrence def DesignFlowInteraction {
		ref part system :>> dateSystem;

		message specSubmission of HDLSpecification
			from system.designFlow.specification
			to system.synthesizer.designIn;

		then message netlistDelivery of SynthesizedNetlist
			from system.synthesizer.netlistOut
			to system.verifier;

		then message patternDelivery of TestPattern
			from system.patternGen.patternOut
			to system.ate.patternIn;

		then message resultDelivery of TestResult
			from system.ate.resultOut
			to system.analyzer;
	}

	verification def DesignFlowVerification {
		private import VerificationCases::*;

		subject systemUnderTest : DATESystem;

		objective verifyDesignFlow {
			verify SynthesisPerformanceRequirement;
			verify TestCoverageRequirement;
		}

		action collectMetrics {
			in part system : DATESystem = systemUnderTest;
			out synthTime : DurationValue;
			out coverage : CoveragePercentage;
		}

		action evaluatePerformance {
			in synthTime : DurationValue = collectMetrics.synthTime;
			in coverage : CoveragePercentage = collectMetrics.coverage;
			out verdict : VerdictKind = PassIf(
				synthTime <= 7200 [s] and coverage >= 95.0
			);
		}

		return verdict : VerdictKind = evaluatePerformance.verdict;
	}
}

// --- Test harness (auto-generated) ---
package ExecutionHarness {
    private import ScalarValues::*;
    private import ISQ::*;
    private import SI::*;
    private import Time::*;
    private import NumericalFunctions::*;
    private import 'Design Automation and Test in Europe System'::*;

    part testSubject : LogicSynthesizer {
        exhibit state sm : DesignFlowLifecycle;
    }

    action orchestrator {
        action generateTestsProbe : TestPatternGenerator {
            // TODO(human): unsupported input type for netlist: unknown (missing declared type)
        }
        first generateTestsProbe;
    }
}

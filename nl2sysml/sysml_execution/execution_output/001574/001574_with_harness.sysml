package SiliceneTransistorSystem {
    private import ScalarValues::*;
    private import ISQ::*;
    private import SI::*;
    
    attribute def HoneycombLattice;
    attribute def BuckledStructure;
    
    attribute def ElectronMobilityUnit :> MeasurementUnit;
    attribute def ElectronVoltUnit :> MeasurementUnit;
    
    value def ElectronMobilityValue :> ISQ::QuantityValue {
        attribute :>> num : Real;
        attribute mRef : ElectronMobilityUnit;
    }
    
    value def BandGapEnergyValue :> ISQ::QuantityValue {
        attribute :>> num : Real;
        attribute mRef : ElectronVoltUnit;
    }
    
    item def Silicene {
        doc /* Two-dimensional allotrope of silicon arranged in a honeycomb lattice structure 
               with unique electronic properties including high carrier mobility and tunable band gap */
        
        attribute latticeStructure : HoneycombLattice;
        attribute bucklingHeight : LengthValue;
        attribute electronMobility : ElectronMobilityValue;
        attribute bandGap : BandGapEnergyValue;
        attribute spinOrbitCoupling : Real;
        attribute layerThickness : LengthValue;
        
        port electricalPort {
            in appliedVoltage : ElectricPotentialValue;
            out conductedCurrent : ElectricCurrentValue;
        }
        
        port thermalPort {
            in ambientTemperature : ThermodynamicTemperatureValue;
            out thermalConductivity : ThermalConductivityValue;
        }
    }
    
    part def MetalContact {
        attribute contactResistance : ResistanceValue;
        attribute workFunction : BandGapEnergyValue;
        port electricalTerminal;
    }
    
    part def DielectricMaterial {
        attribute relativePermittivity : Real;
        attribute thickness : LengthValue;
        attribute breakdownField : ElectricFieldStrengthValue;
        port insulatingInterface;
    }
    
    part def GateElectrode {
        attribute gateCapacitance : CapacitanceValue;
        port controlPort {
            in gateVoltage : ElectricPotentialValue;
            out inducedField : ElectricFieldStrengthValue;
        }
    }
    
    part def SubstrateSupport {
        attribute material : String;
        attribute thermalExpansion : Real;
        port mechanicalBase;
        port thermalBase;
    }
    
    action def ApplyGateBias {
        in gateVoltage : ElectricPotentialValue;
        in dielectricThickness : LengthValue;
        out electricField : ElectricFieldStrengthValue;
    }
    
    action def ModulateCarrierDensity {
        in electricField : ElectricFieldStrengthValue;
        in siliceneMobility : ElectronMobilityValue;
        out carrierConcentration : Real;
    }
    
    action def ConductDrainCurrent {
        in carrierConcentration : Real;
        in drainSourceVoltage : ElectricPotentialValue;
        in channelDimensions : LengthValue;
        out drainCurrent : ElectricCurrentValue;
    }
    
    action def DissipateHeat {
        in powerDissipation : PowerValue;
        in thermalResistance : Real;
        out temperatureRise : ThermodynamicTemperatureValue;
    }
    
    enum def OperatingMode {
        cutoff;
        linear;
        saturation;
    }
    
    part def SiliceneFieldEffectTransistor {
        doc /* High-performance field-effect transistor utilizing silicene as the channel material 
               to achieve superior electron mobility and fast switching characteristics */
        
        attribute deviceWidth : LengthValue;
        attribute deviceLength : LengthValue;
        attribute thresholdVoltage : ElectricPotentialValue;
        attribute transconductance : Real;
        attribute currentMode : OperatingMode;
        attribute appliedGateVoltage : ElectricPotentialValue;
        attribute drainSourceVoltage : ElectricPotentialValue;
        
        item siliceneChannel : Silicene {
            :>> layerThickness = 0.3 [nm];
            :>> bucklingHeight = 0.44 [Angstrom];
        }
        
        part sourceContact : MetalContact {
            :>> contactResistance = 50.0 [Ohm];
        }
        
        part drainContact : MetalContact {
            :>> contactResistance = 50.0 [Ohm];
        }
        
        part gateStack {
            part gateOxide : DielectricMaterial {
                :>> thickness = 1.5 [nm];
                :>> relativePermittivity = 20.0;
            }
            
            part topGate : GateElectrode;
        }
        
        part substrate : SubstrateSupport {
            :>> material = "Silicon Dioxide on Silicon";
        }
        
        port sourceTerminal;
        port drainTerminal;
        port gateTerminal;
        port bulkTerminal;
        
        connection sourceToChannel connect sourceContact.electricalTerminal to siliceneChannel.electricalPort;
        connection drainToChannel connect drainContact.electricalTerminal to siliceneChannel.electricalPort;
        connection gateToOxide connect gateStack.topGate.controlPort to gateStack.gateOxide.insulatingInterface;
        connection oxideToChannel connect gateStack.gateOxide.insulatingInterface to siliceneChannel.electricalPort;
        connection channelToSubstrate connect siliceneChannel.thermalPort to substrate.thermalBase;
        
        state operatingBehavior {
            entry; then offState;
            
            state offState {
                doc /* Transistor is in cutoff mode with negligible drain current */
                entry assign currentMode = OperatingMode::cutoff;
            }
            
            transition turnOn
                first offState
                accept gateSignal : ApplyGateBias
                if gateSignal.gateVoltage > thresholdVoltage
                then linearState;
            
            state linearState {
                doc /* Transistor operates in linear region with drain current proportional to drain-source voltage */
                entry assign currentMode = OperatingMode::linear;
                do action modulateCarriers : ModulateCarrierDensity;
                do action conductCurrent : ConductDrainCurrent;
            }
            
            transition enterSaturation
                first linearState
                if drainSourceVoltage > (appliedGateVoltage - thresholdVoltage)
                then saturationState;
            
            state saturationState {
                doc /* Transistor operates in saturation with drain current independent of drain-source voltage */
                entry assign currentMode = OperatingMode::saturation;
                do action modulateCarriers : ModulateCarrierDensity;
                do action conductCurrent : ConductDrainCurrent;
            }
            
            transition exitSaturation
                first saturationState
                if drainSourceVoltage <= (appliedGateVoltage - thresholdVoltage)
                then linearState;
            
            transition turnOff
                first linearState
                accept gateSignal : ApplyGateBias
                if gateSignal.gateVoltage <= thresholdVoltage
                then offState;
            
            transition turnOffFromSaturation
                first saturationState
                accept gateSignal : ApplyGateBias
                if gateSignal.gateVoltage <= thresholdVoltage
                then offState;
        }
    }
    
    action def TransistorSwitchingOperation {
        doc /* Primary function: Modulate electrical current flow through the silicene channel 
               by applying gate voltage to control carrier density and achieve high-speed switching */
        
        in gateControlVoltage : ElectricPotentialValue;
        in drainSourceBias : ElectricPotentialValue;
        in deviceThreshold : ElectricPotentialValue;
        out outputDrainCurrent : ElectricCurrentValue;
        out switchingDelay : TimeValue;
        out powerConsumption : PowerValue;
        
        first start;
        then action applyGate : ApplyGateBias {
            in gateVoltage = gateControlVoltage;
            in dielectricThickness = 1.5 [nm];
            out electricField;
        }
        then action modulate : ModulateCarrierDensity {
            in electricField = applyGate.electricField;
            in siliceneMobility;
            out carrierConcentration;
        }
        then action conduct : ConductDrainCurrent {
            in carrierConcentration = modulate.carrierConcentration;
            in drainSourceVoltage = drainSourceBias;
            in channelDimensions = 100.0 [nm];
            out drainCurrent;
        }
        then action dissipate : DissipateHeat {
            in powerDissipation;
            in thermalResistance = 1000.0;
            out temperatureRise;
        }
        then assign outputDrainCurrent := conduct.drainCurrent;
        then done;
    }
    
    part siliceneTransistor : SiliceneFieldEffectTransistor {
        doc /* Complete silicene-based transistor system demonstrating high-speed electronic switching 
               with superior performance characteristics compared to conventional silicon devices */
        
        :>> deviceWidth = 1.0 [um];
        :>> deviceLength = 100.0 [nm];
        :>> thresholdVoltage = 0.3 [V];
        
        siliceneChannel {
            :>> electronMobility.num = 1500.0;
            :>> bandGap.num = 0.5;
        }
        
        perform action switchingOperation : TransistorSwitchingOperation {
            in gateControlVoltage;
            in drainSourceBias;
            in deviceThreshold = thresholdVoltage;
            out outputDrainCurrent;
            out switchingDelay;
            out powerConsumption;
        }
    }
    
    requirement def HighMobilityRequirement {
        doc /* The silicene channel shall exhibit electron mobility exceeding 1000 cm²/V·s 
               to enable high-frequency operation */
        subject transistor : SiliceneFieldEffectTransistor;
        require constraint {
            transistor.siliceneChannel.electronMobility.num > 1000.0
        }
    }
    
    requirement def FastSwitchingRequirement {
        doc /* The transistor shall achieve switching times below 1 picosecond 
               for next-generation high-speed applications */
        subject device : SiliceneFieldEffectTransistor;
    }
    
    requirement def LowPowerRequirement {
        doc /* Static power dissipation shall remain below 100 microwatts 
               to enable energy-efficient operation */
        subject device : SiliceneFieldEffectTransistor;
    }
    
    requirement def ScalabilityRequirement {
        doc /* The device architecture shall support scaling to channel lengths 
               below 10 nanometers while maintaining performance */
        subject device : SiliceneFieldEffectTransistor;
        require constraint {
            device.deviceLength.num >= 10.0
        }
    }
    
    requirement def ThermalStabilityRequirement {
        doc /* The silicene channel shall maintain structural integrity 
               at operating temperatures up to 400 Kelvin */
        subject transistor : SiliceneFieldEffectTransistor;
    }
    
    requirement systemPerformanceRequirements {
        doc /* Top-level performance requirements for the silicene transistor system 
               ensuring viability for advanced electronic applications */
        
        require highMobility : HighMobilityRequirement;
        require fastSwitching : FastSwitchingRequirement;
        require lowPower : LowPowerRequirement;
        require scalability : ScalabilityRequirement;
        require thermalStability : ThermalStabilityRequirement;
    }
}

// --- Test harness (auto-generated) ---
package ExecutionHarness {
    private import ScalarValues::*;
    private import ISQ::*;
    private import SI::*;
    private import SiliceneTransistorSystem::*;

    action orchestrator {
        attribute testGateVoltage : ElectricPotentialValue;
        attribute testDielectricThickness : LengthValue;
        action actionProbe : ApplyGateBias {
            in gateVoltage = testGateVoltage;
            in dielectricThickness = testDielectricThickness;
        }
        first actionProbe;
    }
}

package 'Fabry-Perot Interferometer System' {
    private import ScalarValues::*;
    private import ISQ::*;
    private import SI::*;

    attribute def WavelengthValue :> LengthValue;
    attribute def ReflectivityCoefficient :> Real;
    attribute def FinesseValue :> Real;
    attribute def TransmittanceValue :> Real;
    attribute def IntensityValue :> PowerValue;
    attribute def PhaseValue :> Real;
    
    attribute def SystemStart;
    attribute def SystemStop;
    attribute def AlignmentCommand;
    attribute def ScanCommand;
    
    item def OpticalBeam {
        attribute wavelength : WavelengthValue;
        attribute intensity : IntensityValue;
        attribute phase : PhaseValue;
    }
    
    item def TransmissionData {
        attribute wavelength : WavelengthValue;
        attribute transmittance : TransmittanceValue;
        attribute cavitySpacing : LengthValue;
    }

    port def OpticalInputPort {
        in beam : OpticalBeam;
    }
    
    port def OpticalOutputPort {
        out beam : OpticalBeam;
    }
    
    port def ControlInputPort {
        in spacing : LengthValue;
        in alignmentCmd : AlignmentCommand;
    }
    
    port def DataOutputPort {
        out transmissionData : TransmissionData[*];
    }

    part def Mirror {
        doc /* High-reflectivity optical mirror forming cavity boundary. */
        attribute reflectivity : ReflectivityCoefficient;
        attribute surfaceQuality : Real;
        attribute position : LengthValue;
        port opticalInterface : OpticalInputPort;
    }
    
    part def OpticalCavity {
        doc /* Resonant cavity formed by two parallel mirrors. */
        attribute nominalSpacing : LengthValue;
        attribute currentSpacing : LengthValue;
        attribute freeSpectralRange : FrequencyValue;
        attribute finesse : FinesseValue;
        
        port input : OpticalInputPort;
        port output : OpticalOutputPort;
        port control : ControlInputPort;
        
        part frontMirror : Mirror {
            attribute reflectivity = 0.95;
            attribute surfaceQuality = 0.99;
        }
        
        part rearMirror : Mirror {
            attribute reflectivity = 0.95;
            attribute surfaceQuality = 0.99;
        }
        
        constraint spacingRelation {
            currentSpacing == nominalSpacing + (rearMirror.position - frontMirror.position)
        }
        
        constraint finesseCalculation {
            finesse == (3.14159 * 0.9747) / (1.0 - frontMirror.reflectivity * rearMirror.reflectivity)
        }
    }
    
    part def LaserSource {
        doc /* Coherent light source for interferometer input. */
        attribute wavelength : WavelengthValue;
        attribute outputPower : IntensityValue;
        attribute linewidth : FrequencyValue;
        attribute stability : Real;
        port output : OpticalOutputPort;
    }
    
    part def PhotoDetector {
        doc /* Optical detector measuring transmitted intensity. */
        attribute sensitivity : Real;
        attribute responseTime : TimeValue;
        attribute quantumEfficiency : Real;
        port input : OpticalInputPort;
        port dataOut : DataOutputPort;
    }
    
    part def PiezoActuator {
        doc /* Precision actuator for cavity length control. */
        attribute displacement : LengthValue;
        attribute controlVoltage : Real;
        attribute sensitivity : LengthValue;
        port control {
            in voltage : Real;
            out actualDisplacement : LengthValue;
        }
        
        constraint displacementRelation {
            displacement == controlVoltage * sensitivity
        }
    }
    
    part def StabilizationController {
        doc /* Feedback controller maintaining cavity resonance. */
        attribute targetWavelength : WavelengthValue;
        attribute lockPoint : Real;
        attribute gainParameter : Real;
        port sensorInput {
            in measuredIntensity : IntensityValue;
        }
        port actuatorOutput {
            out correctionVoltage : Real;
        }
    }

    action def AlignCavity {
        doc /* Align mirrors to achieve parallelism and optimal coupling. */
        in targetParallelism : Real;
        in inputBeam : OpticalBeam;
        out alignmentQuality : Real;
    }
    
    action def CalculateTransmission {
        doc /* Compute transmitted intensity using Airy function. */
        in wavelength : WavelengthValue;
        in cavitySpacing : LengthValue;
        in finesse : FinesseValue;
        in incidentIntensity : IntensityValue;
        out transmittedIntensity : IntensityValue;
        out transmittance : TransmittanceValue;
    }
    
    action def ScanWavelength {
        doc /* Scan cavity length to measure transmission spectrum. */
        in startSpacing : LengthValue;
        in endSpacing : LengthValue;
        in stepSize : LengthValue;
        in inputBeam : OpticalBeam;
        in finesse : FinesseValue;
        out spectrum : TransmissionData[*];
    }
    
    action def DetectResonance {
        doc /* Identify resonance peaks in transmission spectrum. */
        in transmittance : TransmittanceValue;
        in threshold : Real;
        out isResonant : Boolean;
        out resonanceOrder : Integer;
    }
    
    action def StabilizeCavity {
        doc /* Maintain cavity at resonance using feedback control. */
        in targetIntensity : IntensityValue;
        in measuredIntensity : IntensityValue;
        in gainParameter : Real;
        out correctionSignal : Real;
    }

    action def PerformSpectralAnalysis {
        doc /* Execute complete spectral measurement cycle. */
        in inputBeam : OpticalBeam;
        in cavitySpacing : LengthValue;
        in finesse : FinesseValue;
        out measuredSpectrum : TransmissionData[*];
        out resonantWavelengths : WavelengthValue[*];
        
        first start;
        then merge prepareMeasurement;
        then action align : AlignCavity {
            in targetParallelism = 0.001;
            in inputBeam = PerformSpectralAnalysis::inputBeam;
            out alignmentQuality;
        }
        then decide;
            if align.alignmentQuality > 0.95 then proceedToScan;
            if align.alignmentQuality <= 0.95 then prepareMeasurement;
        action proceedToScan {
            action scan : ScanWavelength {
                in startSpacing = cavitySpacing - 5.0e-6[SI::m];
                in endSpacing = cavitySpacing + 5.0e-6[SI::m];
                in stepSize = 1.0e-9[SI::m];
                in inputBeam = PerformSpectralAnalysis::inputBeam;
                in finesse = PerformSpectralAnalysis::finesse;
                out spectrum;
            }
            flow scan.spectrum to measuredSpectrum;
        }
        then done;
    }
    
    action def OperateInterferometer {
        doc /* Main operational behavior of interferometer system. */
        in sourceBeam : OpticalBeam;
        in nominalSpacing : LengthValue;
        in systemFinesse : FinesseValue;
        out continuousData : TransmissionData[*];
        
        first start;
        accept systemStart : SystemStart;
        then merge operationalLoop;
        action measureTransmission : CalculateTransmission {
            in wavelength = sourceBeam.wavelength;
            in cavitySpacing = nominalSpacing;
            in finesse = systemFinesse;
            in incidentIntensity = sourceBeam.intensity;
            out transmittedIntensity;
            out transmittance;
        }
        then action stabilize : StabilizeCavity {
            in targetIntensity = sourceBeam.intensity * 0.9;
            in measuredIntensity = measureTransmission.transmittedIntensity;
            in gainParameter = 0.5;
            out correctionSignal;
        }
        then operationalLoop;
        accept systemStop : SystemStop;
        then done;
    }

    part def FabryPerotInterferometer {
        doc /* 
            Complete Fabry-Perot interferometer system for high-resolution 
            spectral analysis and wavelength filtering using optical interference.
        */
        
        port opticalInput : OpticalInputPort;
        port opticalOutput : OpticalOutputPort;
        port measurementOutput : DataOutputPort;
        port systemControl : ControlInputPort;
        
        attribute operatingWavelength : WavelengthValue;
        attribute spectralResolution : FrequencyValue;
        
        part source : LaserSource {
            attribute wavelength = 632.8e-9[SI::m];
            attribute outputPower = 1.0e-3[SI::W];
            attribute linewidth = 1.0e6[SI::Hz];
            attribute stability = 0.99;
        }
        
        part cavity : OpticalCavity {
            attribute nominalSpacing = 10.0e-3[SI::m];
            attribute currentSpacing = 10.0e-3[SI::m];
            attribute freeSpectralRange = 15.0e9[SI::Hz];
            attribute finesse = 30.0;
        }
        
        part detector : PhotoDetector {
            attribute sensitivity = 0.9;
            attribute responseTime = 1.0e-6[SI::s];
            attribute quantumEfficiency = 0.85;
        }
        
        part actuator : PiezoActuator {
            attribute displacement = 0.0[SI::m];
            attribute controlVoltage = 0.0;
            attribute sensitivity = 10.0e-9[SI::m];
        }
        
        part controller : StabilizationController {
            attribute targetWavelength = 632.8e-9[SI::m];
            attribute lockPoint = 0.5;
            attribute gainParameter = 0.5;
        }
        
        connect source.output to cavity.input;
        connect cavity.output to detector.input;
        connect detector.dataOut to measurementOutput;
        connect systemControl to cavity.control;
        
        perform action operation : OperateInterferometer {
            in sourceBeam {
                attribute wavelength = source.wavelength;
                attribute intensity = source.outputPower;
                attribute phase = 0.0;
            }
            in nominalSpacing = cavity.nominalSpacing;
            in systemFinesse = cavity.finesse;
            out continuousData;
        }
        
        constraint resolutionRequirement {
            spectralResolution == cavity.freeSpectralRange / cavity.finesse
        }
    }

    requirement def SpectralResolutionRequirement {
        doc /* System shall achieve specified spectral resolution. */
        attribute requiredResolution : FrequencyValue;
    }
    
    requirement def TransmissionEfficiencyRequirement {
        doc /* System shall maintain minimum transmission at resonance. */
        attribute minimumTransmittance : Real;
    }
    
    requirement def StabilityRequirement {
        doc /* Cavity length shall remain stable during operation. */
        attribute maximumDrift : LengthValue;
    }
    
    requirement <'FP-001'> highResolution : SpectralResolutionRequirement {
        doc /* 
            The interferometer shall achieve spectral resolution 
            better than 500 MHz at 633 nm wavelength.
        */
        attribute requiredResolution = 500.0e6[SI::Hz];
        
        subject interferometerSystem : FabryPerotInterferometer;
        
        require constraint {
            interferometerSystem.spectralResolution < requiredResolution
        }
    }
    
    requirement <'FP-002'> highTransmission : TransmissionEfficiencyRequirement {
        doc /* 
            The system shall achieve peak transmittance greater than 
            85% at resonance wavelengths.
        */
        attribute minimumTransmittance = 0.85;
        
        subject interferometerSystem : FabryPerotInterferometer;
    }
    
    requirement <'FP-003'> cavityStability : StabilityRequirement {
        doc /* 
            The cavity length shall be stabilized to within 0.5 nm 
            during measurement operations.
        */
        attribute maximumDrift = 0.5e-9[SI::m];
        
        subject interferometerSystem : FabryPerotInterferometer;
        
        require constraint {
            interferometerSystem.cavity.currentSpacing - 
                interferometerSystem.cavity.nominalSpacing < maximumDrift
        }
    }
    
    requirement <'FP-SYS'> systemMission {
        doc /* 
            The Fabry-Perot interferometer system shall perform high-resolution
            spectral analysis by utilizing constructive and destructive interference
            between parallel mirrors to selectively transmit wavelengths satisfying
            resonance conditions, enabling precise wavelength filtering and measurement.
        */
        
        subject interferometerSystem : FabryPerotInterferometer;
        
        assume constraint sourceCoherence {
            interferometerSystem.source.linewidth < 10.0e6[SI::Hz]
        }
        
        assume constraint mirrorQuality {
            interferometerSystem.cavity.frontMirror.reflectivity > 0.9 and
            interferometerSystem.cavity.rearMirror.reflectivity > 0.9
        }
        
        require highResolution;
        require highTransmission;
        require cavityStability;
    }

    part interferometerSystem : FabryPerotInterferometer {
        doc /* 
            Operational Fabry-Perot interferometer configured for 
            visible wavelength spectral analysis.
        */
        
        attribute operatingWavelength = 632.8e-9[SI::m];
        attribute spectralResolution = 500.0e6[SI::Hz];
    }
    
    satisfy systemMission by interferometerSystem;
}

// --- Test harness (auto-generated) ---
package ExecutionHarness {
    private import ScalarValues::*;
    private import ISQ::*;
    private import SI::*;
    private import 'Fabry-Perot Interferometer System'::*;

    action orchestrator {
        attribute testStartSpacing : LengthValue;
        attribute testEndSpacing : LengthValue;
        attribute testStepSize : LengthValue;
        item testInputBeam : OpticalBeam {
            attribute wavelength : WavelengthValue;
            attribute intensity : IntensityValue;
            attribute phase : PhaseValue = 0.0;
        }
        attribute testFinesse : FinesseValue = 0.0;
        action scanProbe : ScanWavelength {
            in startSpacing = testStartSpacing;
            in endSpacing = testEndSpacing;
            in stepSize = testStepSize;
            in inputBeam = testInputBeam;
            in finesse = testFinesse;
        }
        first scanProbe;
    }
}

package P1 {
	part def A;
}

package P2 {
	private import P1::*;
	part a : A;
}

private import P2::*;

package P3 {
	part b subsets a;
}

// --- Test harness (auto-generated) ---
package ExecutionHarness {
    private import P1::*;
    part testSubject : A;
}

package 'Time Constraints' {
	private import ISQ::TemperatureValue;
	private import ISQ::DurationValue;
	private import Time::TimeInstantValue;
	private import Time::TimeOf;
	private import Time::DurationOf;
	private import SI::h;
	private import SI::s;

	attribute def MaintenanceDone;
	
	part def Vehicle {
		attribute maintenanceTime : TimeInstantValue;
		attribute maintenanceInterval : DurationValue;
		attribute maxTemperature : TemperatureValue;
	}
	
	state healthStates {
		in vehicle : Vehicle;
		
		entry; then normal;
		
		state normal;
		accept at vehicle.maintenanceTime
			then maintenance;
		
		state maintenance {
			assert constraint { TimeOf(maintenance) > vehicle.maintenanceTime }
			assert constraint { TimeOf(maintenance) - TimeOf(normal.done) < 2 [s] }
			entry assign vehicle.maintenanceTime := vehicle.maintenanceTime + vehicle.maintenanceInterval;
		}
		accept MaintenanceDone
			then normal;
		
		constraint { DurationOf(maintenance) <= 48 [h] }
	}
}

// --- Test harness (auto-generated) ---
package ExecutionHarness {
    private import ISQ::TemperatureValue;
    private import ISQ::DurationValue;
    private import Time::TimeInstantValue;
    private import Time::TimeOf;
    private import Time::DurationOf;
    private import SI::h;
    private import SI::s;
    private import 'Time Constraints'::*;
    part testSubject : Vehicle;
    // TODO(human): define boundary input values for: maintenanceTime, maintenanceInterval, maxTemperature
    // TODO(human): assert constraint assert_constraint_27 { testSubject.<attr> <= <limit> }
    // TODO(human): assert constraint assert_constraint_28 { testSubject.<attr> <= <limit> }
}

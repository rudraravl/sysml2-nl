package TechnologicalEvolutionSystem {
	private import ScalarValues::*;
	private import ISQ::*;
	private import SI::*;
	
	attribute def EfficiencyRating :> Real;
	attribute def ThroughputRate :> ISQ::FrequencyValue;
	attribute def ProcessingLatency :> ISQ::DurationValue;
	attribute def EnergyConsumption :> ISQ::PowerValue;
	attribute def DataVolume :> ISQ::InformationValue;
	
	item def InputData {
		attribute volume : DataVolume;
		attribute priority : Integer;
		attribute timestamp : ISQ::TimeValue;
	}
	
	item def ProcessedOutput {
		attribute result : String;
		attribute quality : Real;
		attribute processingDuration : ProcessingLatency;
	}
	
	item def EvolutionCommand {
		attribute targetGeneration : Integer;
		attribute transitionMode : String;
	}
	
	item def SystemStatus {
		attribute currentGeneration : Integer;
		attribute operationalEfficiency : EfficiencyRating;
		attribute throughput : ThroughputRate;
	}
	
	port def DataInputPort {
		in item dataStream : InputData;
	}
	
	port def DataOutputPort {
		out item processedData : ProcessedOutput;
	}
	
	port def ControlPort {
		in item command : EvolutionCommand;
		out item status : SystemStatus;
	}
	
	port def PowerPort {
		in attribute powerSupply : EnergyConsumption;
	}
	
	part def FirstGenerationProcessor {
		attribute processingSpeed : ThroughputRate;
		attribute powerDraw : EnergyConsumption;
		attribute efficiency : EfficiencyRating;
		port dataIn : DataInputPort;
		port dataOut : DataOutputPort;
		port power : PowerPort;
	}
	
	part def SecondGenerationProcessor {
		attribute processingSpeed : ThroughputRate;
		attribute powerDraw : EnergyConsumption;
		attribute efficiency : EfficiencyRating;
		attribute parallelChannels : Integer;
		port dataIn : DataInputPort;
		port dataOut : DataOutputPort;
		port power : PowerPort;
		port control : ControlPort;
	}
	
	part def ThirdGenerationProcessor {
		attribute processingSpeed : ThroughputRate;
		attribute powerDraw : EnergyConsumption;
		attribute efficiency : EfficiencyRating;
		attribute parallelChannels : Integer;
		attribute adaptiveOptimization : Boolean;
		port dataIn : DataInputPort;
		port dataOut : DataOutputPort;
		port power : PowerPort;
		port control : ControlPort;
	}
	
	part def EvolutionController {
		attribute activeGeneration : Integer;
		attribute transitionInProgress : Boolean;
		port controlGen2 : ControlPort;
		port controlGen3 : ControlPort;
		port systemControl : ControlPort;
	}
	
	part def PerformanceAnalyzer {
		attribute measuredThroughput : ThroughputRate;
		attribute measuredLatency : ProcessingLatency;
		attribute measuredEfficiency : EfficiencyRating;
		attribute evolutionThreshold : Real;
	}
	
	action def ProcessDataGen1 {
		in data : InputData;
		in speed : ThroughputRate;
		out result : ProcessedOutput;
	}
	
	action def ProcessDataGen2 {
		in data : InputData;
		in speed : ThroughputRate;
		in channels : Integer;
		out result : ProcessedOutput;
	}
	
	action def ProcessDataGen3 {
		in data : InputData;
		in speed : ThroughputRate;
		in channels : Integer;
		in adaptive : Boolean;
		out result : ProcessedOutput;
	}
	
	action def AnalyzePerformance {
		in throughput : ThroughputRate;
		in latency : ProcessingLatency;
		in efficiency : EfficiencyRating;
		out performanceScore : Real;
	}
	
	action def TriggerEvolution {
		in currentGen : Integer;
		in performanceScore : Real;
		in threshold : Real;
		out shouldEvolve : Boolean;
		out targetGen : Integer;
	}
	
	action def TransitionGeneration {
		in fromGen : Integer;
		in toGen : Integer;
		out transitionComplete : Boolean;
	}
	
	state def SystemGenerationStates {
		entry; then generation1;
		
		state generation1 {
			entry assign currentEfficiency := 0.55;
			entry assign currentThroughput := 1000.0;
		}
		
		transition gen1_to_gen2
			first generation1
			if currentEfficiency < 0.65
			then generation2;
		
		state generation2 {
			entry assign currentEfficiency := 0.75;
			entry assign currentThroughput := 3000.0;
		}
		
		transition gen2_to_gen3
			first generation2
			if currentEfficiency < 0.85
			then generation3;
		
		state generation3 {
			entry assign currentEfficiency := 0.95;
			entry assign currentThroughput := 8000.0;
		}
		
		attribute currentEfficiency : Real;
		attribute currentThroughput : Real;
	}
	
	action def EvolutionaryDataProcessing {
		first start;
		then merge operationLoop;
		
		action analyzeSystem : AnalyzePerformance {
			in throughput;
			in latency;
			in efficiency;
			out performanceScore;
		}
		
		then action evaluateEvolution : TriggerEvolution {
			in currentGen = activeGeneration;
			in performanceScore = analyzeSystem.performanceScore;
			in threshold = evolutionThreshold;
			out shouldEvolve;
			out targetGen;
		}
		
		then decide;
			if evaluateEvolution.shouldEvolve then initiateTransition;
			if !evaluateEvolution.shouldEvolve then processWithCurrentGen;
		
		action initiateTransition : TransitionGeneration {
			in fromGen = activeGeneration;
			in toGen = evaluateEvolution.targetGen;
			out transitionComplete;
		}
		then processWithCurrentGen;
		
		action processWithCurrentGen {
			in inputData : InputData;
			out outputData : ProcessedOutput;
		}
		
		then operationLoop;
		then done;
		
		in attribute throughput : ThroughputRate;
		in attribute latency : ProcessingLatency;
		in attribute efficiency : EfficiencyRating;
		in attribute activeGeneration : Integer;
		in attribute evolutionThreshold : Real;
		in attribute inputData : InputData;
		out attribute outputData : ProcessedOutput;
	}
	
	part def EvolutionaryProcessingPlatform {
		doc /*
			This system represents a technological evolution platform that autonomously
			advances through three distinct processing generations. The primary function
			is to continuously process data streams while monitoring performance metrics
			and automatically transitioning to more advanced processing architectures
			when efficiency thresholds are reached. Each generation offers improved
			throughput, reduced latency, and higher energy efficiency, demonstrating
			progressive technological advancement.
		*/
		
		attribute systemIdentifier : String;
		
		part gen1Processor : FirstGenerationProcessor;
		part gen2Processor : SecondGenerationProcessor;
		part gen3Processor : ThirdGenerationProcessor;
		part evolutionControl : EvolutionController;
		part performanceMonitor : PerformanceAnalyzer;
	}
	
	part evolutionaryProcessingSystem : EvolutionaryProcessingPlatform {
		attribute :>> systemIdentifier = "Evolutionary Processing Platform v3.0";
		
		perform action continuousEvolution[*] ordered : EvolutionaryDataProcessing;
		
		part :>> gen1Processor {
			attribute :>> processingSpeed = 1000.0 [SI::Hz];
			attribute :>> powerDraw = 200.0 [SI::W];
			attribute :>> efficiency = 0.55;
			perform continuousEvolution.processWithCurrentGen;
		}
		
		part :>> gen2Processor {
			attribute :>> processingSpeed = 3500.0 [SI::Hz];
			attribute :>> powerDraw = 180.0 [SI::W];
			attribute :>> efficiency = 0.75;
			attribute :>> parallelChannels = 4;
			perform continuousEvolution.processWithCurrentGen;
		}
		
		part :>> gen3Processor {
			attribute :>> processingSpeed = 10000.0 [SI::Hz];
			attribute :>> powerDraw = 150.0 [SI::W];
			attribute :>> efficiency = 0.95;
			attribute :>> parallelChannels = 16;
			attribute :>> adaptiveOptimization = true;
			perform continuousEvolution.processWithCurrentGen;
		}
		
		part :>> evolutionControl {
			attribute :>> activeGeneration = 1;
			attribute :>> transitionInProgress = false;
			perform continuousEvolution.evaluateEvolution;
			perform continuousEvolution.initiateTransition;
		}
		
		part :>> performanceMonitor {
			attribute :>> measuredThroughput = 1000.0 [SI::Hz];
			attribute :>> measuredLatency = 10.0 [SI::ms];
			attribute :>> measuredEfficiency = 0.55;
			attribute :>> evolutionThreshold = 0.7;
			perform continuousEvolution.analyzeSystem;
		}
		
		connect gen1Processor.dataOut to evolutionControl.systemControl;
		connect gen2Processor.control to evolutionControl.controlGen2;
		connect gen3Processor.control to evolutionControl.controlGen3;
	}
	
	requirement def PerformanceEvolutionRequirement {
		doc /* The system shall demonstrate measurable performance improvement across generations. */
		attribute minimumEfficiencyGain : Real;
		attribute minimumThroughputGain : Real;
	}
	
	requirement def AutonomousTransitionRequirement {
		doc /* The system shall autonomously transition between generations based on performance metrics. */
		attribute maxTransitionTime : ISQ::DurationValue;
		attribute transitionReliability : Real;
	}
	
	requirement def EnergyEfficiencyRequirement {
		doc /* Each generation shall reduce power consumption while increasing performance. */
		attribute maxPowerPerThroughput : Real;
	}
	
	requirement <'REQ-001'> performanceEvolution : PerformanceEvolutionRequirement {
		attribute :>> minimumEfficiencyGain = 0.15;
		attribute :>> minimumThroughputGain = 2.0;
		
		subject system : EvolutionaryProcessingPlatform;
		
		require constraint {
			system.gen2Processor.efficiency >= 
				system.gen1Processor.efficiency + 0.15 and
			system.gen3Processor.efficiency >= 
				system.gen2Processor.efficiency + 0.15
		}
	}
	
	requirement <'REQ-002'> autonomousTransition : AutonomousTransitionRequirement {
		attribute :>> maxTransitionTime = 5.0 [SI::s];
		attribute :>> transitionReliability = 0.99;
		
		subject controller : EvolutionController;
		
		require constraint {
			controller.activeGeneration >= 1 and
			controller.activeGeneration <= 3
		}
	}
	
	requirement <'REQ-003'> energyEfficiency : EnergyEfficiencyRequirement {
		attribute :>> maxPowerPerThroughput = 0.2;
		
		subject system : EvolutionaryProcessingPlatform;
		
		require constraint {
			system.gen3Processor.powerDraw < 
				system.gen1Processor.powerDraw
		}
	}
	
	requirement <'MISSION-001'> primarySystemMission {
		doc /* 
			The Evolutionary Processing System shall autonomously process continuous
			data streams while monitoring its own performance metrics and automatically
			advancing through three distinct technological generations. The system begins
			with first-generation processing capabilities and progressively evolves to
			second and third-generation architectures when performance analysis indicates
			efficiency thresholds have been reached. Each evolutionary transition shall
			deliver measurable improvements in throughput, latency, and energy efficiency
			while maintaining uninterrupted data processing operations.
		*/
		
		subject system : EvolutionaryProcessingPlatform;
		
		assume constraint initialState {
			doc /* System initializes in first-generation processing mode. */
			system.evolutionControl.activeGeneration == 1
		}
		
		require performanceEvolution;
		require autonomousTransition;
		require energyEfficiency;
		
		verify constraint evolutionCapability {
			doc /* System demonstrates full evolutionary progression capability. */
			system.gen1Processor.processingSpeed < 
				system.gen2Processor.processingSpeed and
			system.gen2Processor.processingSpeed < 
				system.gen3Processor.processingSpeed and
			system.gen3Processor.efficiency > 0.9
		}
	}
}

// --- Test harness (auto-generated) ---
package ExecutionHarness {
    private import ScalarValues::*;
    private import ISQ::*;
    private import SI::*;
    private import TechnologicalEvolutionSystem::*;

    part testSubject : FirstGenerationProcessor {
        exhibit state sm : SystemGenerationStates;
    }

    action orchestrator {
        attribute testThroughput : ThroughputRate;
        attribute testLatency : ProcessingLatency;
        attribute testEfficiency : EfficiencyRating = 0.0;
        action analyzeSystemProbe : AnalyzePerformance {
            in throughput = testThroughput;
            in latency = testLatency;
            in efficiency = testEfficiency;
        }
        first analyzeSystemProbe;
    }
}

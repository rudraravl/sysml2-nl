package ExploratoryEngineeringSystem {
    private import ScalarValues::*;
    private import ISQ::*;
    private import SI::*;

    package Definitions {
        attribute def DesignScore {
            attribute feasibility: Real;
            attribute performance: Real;
            attribute cost: Real;
            attribute risk: Real;
            attribute overall: Real;
        }

        item def DesignConcept {
            attribute conceptId: String;
            attribute mass: MassValue;
            attribute power: PowerValue;
            attribute efficiency: Real;
            attribute complexity: Integer;
            attribute maturityLevel: Integer;
        }

        item def AnalysisResult {
            attribute conceptId: String;
            attribute score: DesignScore;
            attribute feasible: Boolean;
            attribute timestamp: TimeValue;
        }

        item def OptimizationParameters {
            attribute maxIterations: Integer;
            attribute convergenceTolerance: Real;
            attribute populationSize: Integer;
        }

        port def ConceptPort {
            in concept: DesignConcept;
            out evaluatedConcept: DesignConcept;
        }

        port def AnalysisPort {
            in request: DesignConcept;
            out result: AnalysisResult;
        }

        port def DataPort {
            out data: AnalysisResult;
        }

        interface def ConceptInterface {
            end source: ConceptPort;
            end target: ConceptPort;
        }

        interface def AnalysisInterface {
            end requester: AnalysisPort;
            end analyzer: AnalysisPort;
        }

        action def GenerateVariants {
            in baseConcept: DesignConcept;
            in variationCount: Integer;
            out variants: DesignConcept[*] ordered;
        }

        action def EvaluateFeasibility {
            in concept: DesignConcept;
            out feasibilityScore: Real;
            out feasible: Boolean;
        }

        action def PerformTradeStudy {
            in concepts: DesignConcept[*] ordered;
            out rankedConcepts: DesignConcept[*] ordered;
            out bestConcept: DesignConcept;
        }

        action def OptimizeDesign {
            in initialConcept: DesignConcept;
            in parameters: OptimizationParameters;
            out optimizedConcept: DesignConcept;
        }

        action def ValidatePerformance {
            in concept: DesignConcept;
            out performanceScore: Real;
            out meetsRequirements: Boolean;
        }

        part def ConceptGenerator {
            port conceptOut: ConceptPort;
            
            action def Generate {
                in seed: DesignConcept;
                out newConcepts: DesignConcept[*] ordered;
            }
            
            perform action generate: Generate;
        }

        part def FeasibilityAnalyzer {
            port analysisIn: AnalysisPort;
            port analysisOut: AnalysisPort;
            
            action def Analyze {
                in concept: DesignConcept;
                out result: AnalysisResult;
            }
            
            perform action analyze: Analyze;
        }

        part def TradeStudyEngine {
            port conceptIn: ConceptPort;
            port dataOut: DataPort;
            
            action def RankConcepts {
                in concepts: DesignConcept[*] ordered;
                out ranked: DesignConcept[*] ordered;
            }
            
            perform action rank: RankConcepts;
        }

        part def OptimizationEngine {
            port conceptIn: ConceptPort;
            port conceptOut: ConceptPort;
            
            action def Optimize {
                in concept: DesignConcept;
                out optimized: DesignConcept;
            }
            
            perform action optimize: Optimize;
        }

        part def PerformanceValidator {
            port analysisIn: AnalysisPort;
            
            action def Validate {
                in concept: DesignConcept;
                out valid: Boolean;
            }
            
            perform action validate: Validate;
        }

        part def KnowledgeRepository {
            attribute storedConcepts: Integer;
            attribute storedResults: Integer;
            
            action def StoreConcept {
                in concept: DesignConcept;
                out stored: Boolean;
            }
            
            action def RetrieveConcepts {
                in query: String;
                out concepts: DesignConcept[*] ordered;
            }
            
            perform action store: StoreConcept;
            perform action retrieve: RetrieveConcepts;
        }

        part def ExploratoryEngineeringPlatform {
            attribute totalConceptsEvaluated: Integer;
            attribute explorationTime: TimeValue;
            attribute bestScore: Real;
            
            part generator: ConceptGenerator {
                port :>> conceptOut;
            }
            
            part analyzer: FeasibilityAnalyzer {
                port :>> analysisIn;
                port :>> analysisOut;
            }
            
            part tradeStudy: TradeStudyEngine {
                port :>> conceptIn;
                port :>> dataOut;
            }
            
            part optimizer: OptimizationEngine {
                port :>> conceptIn;
                port :>> conceptOut;
            }
            
            part validator: PerformanceValidator {
                port :>> analysisIn;
            }
            
            part repository: KnowledgeRepository;
            
            interface genToAnalyzer: ConceptInterface
                connect generator.conceptOut to analyzer.analysisIn;
            
            interface analyzerToTrade: ConceptInterface
                connect analyzer.analysisOut to tradeStudy.conceptIn;
            
            interface tradeToOptimizer: ConceptInterface
                connect tradeStudy.conceptIn to optimizer.conceptIn;
            
            interface optimizerToValidator: AnalysisInterface
                connect optimizer.conceptOut to validator.analysisIn;
        }

        action def ExploreDesignSpace {
            in initialConcept: DesignConcept;
            in maxIterations: Integer;
            out finalConcept: DesignConcept;
            out explorationComplete: Boolean;
            
            first start;
            then merge explorationLoop;
            
            action generateVariants: GenerateVariants {
                in baseConcept = initialConcept;
                in variationCount = 5;
                out variants: DesignConcept[*];
            }
            
            then action evaluateFeasibility: EvaluateFeasibility {
                in concept;
                out feasibilityScore: Real;
                out feasible: Boolean;
            }
            
            then decide;
                if evaluateFeasibility.feasible then performTrade;
                if not evaluateFeasibility.feasible then explorationLoop;
            
            action performTrade: PerformTradeStudy {
                in concepts = generateVariants.variants;
                out rankedConcepts: DesignConcept[*];
                out bestConcept: DesignConcept;
            }
            
            then action optimizeDesign: OptimizeDesign {
                in initialConcept = performTrade.bestConcept;
                in parameters: OptimizationParameters;
                out optimizedConcept: DesignConcept;
            }
            
            then action validatePerformance: ValidatePerformance {
                in concept = optimizeDesign.optimizedConcept;
                out performanceScore: Real;
                out meetsRequirements: Boolean;
            }
            
            then decide;
                if validatePerformance.meetsRequirements then complete;
                if not validatePerformance.meetsRequirements then checkIterations;
            
            action checkIterations;
            then decide;
                if checkIterations then explorationLoop;
                if not checkIterations then complete;
            
            then explorationLoop;
            
            action complete {
                out :>> finalConcept = optimizeDesign.optimizedConcept;
                out :>> explorationComplete = true;
            }
            
            then done;
        }
    }

    package Requirements {
        public import Definitions::*;
        
        requirement def <'EXP-1'> ExplorationCapability {
            doc /* The system shall explore multiple design concepts and identify feasible solutions. */
            subject platform: ExploratoryEngineeringPlatform;
            attribute minConceptsEvaluated: Integer;
            attribute actualConceptsEvaluated: Integer = platform.totalConceptsEvaluated;
            require constraint {
                actualConceptsEvaluated >= minConceptsEvaluated
            }
        }
        
        requirement def <'EXP-2'> PerformanceOptimization {
            doc /* The system shall optimize design concepts to achieve best performance score. */
            subject platform: ExploratoryEngineeringPlatform;
            attribute minScore: Real;
            attribute achievedScore: Real = platform.bestScore;
            require constraint {
                achievedScore >= minScore
            }
        }
        
        requirement def <'EXP-3'> TimeConstraint {
            doc /* The exploration process shall complete within allocated time. */
            subject platform: ExploratoryEngineeringPlatform;
            attribute maxTime: TimeValue;
            attribute actualTime: TimeValue = platform.explorationTime;
            require constraint {
                actualTime <= maxTime
            }
        }
        
        requirement <'EXP-SYS'> systemRequirements {
            doc /* Top-level requirements for exploratory engineering platform. */
            subject platform: ExploratoryEngineeringPlatform;
            
            require explorationReq: ExplorationCapability {
                subject :>> platform;
                attribute :>> minConceptsEvaluated = 10;
            }
            
            require performanceReq: PerformanceOptimization {
                subject :>> platform;
                attribute :>> minScore = 0.75;
            }
            
            require timeReq: TimeConstraint {
                subject :>> platform;
                attribute :>> maxTime = 3600 [s];
            }
        }
    }

    package Instances {
        public import Definitions::*;
        public import Requirements::*;
        
        part exploratoryPlatform: ExploratoryEngineeringPlatform {
            doc /* 
             * Exploratory engineering platform for systematic investigation
             * of novel design concepts through automated generation, analysis,
             * and optimization of design alternatives.
             */
            
            attribute :>> totalConceptsEvaluated = 0;
            attribute :>> explorationTime = 0 [s];
            attribute :>> bestScore = 0.0;
            
            perform action exploration: ExploreDesignSpace {
                in initialConcept: DesignConcept {
                    attribute :>> conceptId = "SEED-001";
                    attribute :>> mass = 1000 [kg];
                    attribute :>> power = 50000 [W];
                    attribute :>> efficiency = 0.85;
                    attribute :>> complexity = 5;
                    attribute :>> maturityLevel = 3;
                }
                in maxIterations = 20;
                out finalConcept: DesignConcept;
                out explorationComplete: Boolean;
            }
            
            part :>> generator {
                perform exploration.generateVariants :>> generate;
            }
            
            part :>> analyzer {
                perform exploration.evaluateFeasibility :>> analyze;
            }
            
            part :>> tradeStudy {
                perform exploration.performTrade :>> rank;
            }
            
            part :>> optimizer {
                perform exploration.optimizeDesign :>> optimize;
            }
            
            part :>> validator {
                perform exploration.validatePerformance :>> validate;
            }
            
            part :>> repository {
                attribute :>> storedConcepts = 0;
                attribute :>> storedResults = 0;
            }
        }
    }
}

// --- Test harness (auto-generated) ---
package ExecutionHarness {
    private import ScalarValues::*;
    private import ISQ::*;
    private import SI::*;
    private import ExploratoryEngineeringSystem::*;

    action orchestrator {
        item testBaseConcept : DesignConcept {
            attribute conceptId = "";
            attribute mass : MassValue;
            attribute power : PowerValue;
            attribute efficiency = 0.0;
            attribute complexity = 0;
            attribute maturityLevel = 0;
        }
        action generateVariantsProbe : GenerateVariants {
            in baseConcept = testBaseConcept;
            in variationCount = 0;
        }
        first generateVariantsProbe;
    }
}

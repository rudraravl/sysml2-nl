action def ControlNodeTest {
	action A1;
	then J;
	
	action A2 {
	    out a;
	}
	then J;
	
	flow A2.a to F.a;
	
	join J;
	then fork F {
	    in a;
	    out b1;
	    out b2;
	}
	then B1;
	then B2;
	
	flow F.b1 to B1.b;
	flow F.b2 to B2.b;
		
	action B1 {
	    in b;
	}
	then M;
	
	action B2 {
	    in b;
	}
	then M; 
	
	merge M;
}

// --- Test harness (auto-generated) ---
package ExecutionHarness {

    action orchestrator {
        action actionProbe : ControlNodeTest {
            // TODO(human): unsupported input type for a: unknown (missing declared type)
            // TODO(human): unsupported input type for b: unknown (missing declared type)
            // TODO(human): unsupported input type for b: unknown (missing declared type)
        }
        first actionProbe;
    }
}

package 'Molecular Assembler System' {
	private import ScalarValues::*;
	private import ISQ::*;
	private import SI::*;
	
	attribute def AtomType;
	attribute def MolecularBlueprint;
	attribute def BondType;
	attribute def AssemblyStatus;
	
	attribute def AtomicPrecision :> LengthValue {
		doc /* Positioning precision at atomic scale in nanometers */
	}
	
	attribute def AssemblyRate :> Real {
		doc /* Number of atoms positioned per second */
	}
	
	item def Atom {
		attribute atomType : AtomType;
		attribute mass : MassValue;
		attribute position : PositionVector;
	}
	
	item def PositionVector {
		attribute x : LengthValue;
		attribute y : LengthValue;
		attribute z : LengthValue;
	}
	
	item def Feedstock {
		attribute availableAtoms : Atom[*];
		attribute purity : Real;
		attribute temperature : ThermodynamicTemperatureValue;
	}
	
	item def TargetStructure {
		attribute blueprint : MolecularBlueprint;
		attribute requiredAtoms : AtomType[*] ordered;
		attribute bondingSequence : BondType[*] ordered;
	}
	
	item def AssembledProduct {
		attribute structure : MolecularBlueprint;
		attribute actualAtoms : Atom[*];
		attribute mass : MassValue;
		attribute defectCount : Integer;
		attribute qualityScore : Real;
	}
	
	port def FeedstockPort {
		in item feedstock : Feedstock;
	}
	
	port def ProductPort {
		out item product : AssembledProduct;
	}
	
	port def ControlPort {
		in attribute blueprint : MolecularBlueprint;
		in attribute startCommand : Boolean;
		out attribute status : AssemblyStatus;
		out attribute progress : Real;
	}
	
	port def PowerPort {
		in attribute power : PowerValue;
	}
	
	part def AtomicManipulator {
		doc /* Precision positioning system for individual atoms */
		
		attribute positioningPrecision : AtomicPrecision;
		attribute maxReach : LengthValue;
		attribute operatingTemperature : ThermodynamicTemperatureValue;
		
		port controlIn : ControlPort;
		port powerIn : PowerPort;
		
		perform action positionAtom {
			in atom : Atom;
			in targetPosition : PositionVector;
			out positioned : Boolean;
			out actualPosition : PositionVector;
		}
	}
	
	part def BondingUnit {
		doc /* System for forming chemical bonds between atoms */
		
		attribute bondingEnergy : EnergyValue;
		attribute bondingAccuracy : Real;
		
		perform action formBond {
			in atom1 : Atom;
			in atom2 : Atom;
			in bondType : BondType;
			out bondFormed : Boolean;
			out bondStrength : EnergyValue;
		}
	}
	
	part def VerificationScanner {
		doc /* Real-time verification of assembly accuracy */
		
		attribute scanResolution : AtomicPrecision;
		attribute scanRate : FrequencyValue;
		
		perform action verifyStructure {
			in currentStructure : AssembledProduct;
			in targetStructure : TargetStructure;
			out verified : Boolean;
			out defects : Integer;
			out qualityScore : Real;
		}
	}
	
	part def FeedstockProcessor {
		doc /* Prepares and sorts atomic feedstock */
		
		port feedstockIn : FeedstockPort;
		
		perform action processAtoms {
			in rawFeedstock : Feedstock;
			out sortedAtoms : Atom[*];
			out processingEfficiency : Real;
		}
	}
	
	part def AssemblyController {
		doc /* Central control system coordinating assembly operations */
		
		attribute currentBlueprint : MolecularBlueprint;
		attribute assemblyProgress : Real;
		attribute errorCount : Integer;
		
		port controlOut : ControlPort;
		
		perform action coordinateAssembly {
			in targetStructure : TargetStructure;
			out assemblyCommands : AssemblyStatus;
			out progressStatus : Real;
		}
	}
	
	action def SelectAtom {
		in feedstock : Feedstock;
		in requiredType : AtomType;
		out selectedAtom : Atom;
		out remainingFeedstock : Feedstock;
	}
	
	action def PositionAtomPrecisely {
		in atom : Atom;
		in targetPosition : PositionVector;
		in precision : AtomicPrecision;
		out positionedAtom : Atom;
		out positionError : LengthValue;
	}
	
	action def FormChemicalBond {
		in atom1 : Atom;
		in atom2 : Atom;
		in bondType : BondType;
		in bondingEnergy : EnergyValue;
		out bondFormed : Boolean;
		out bondStrength : EnergyValue;
	}
	
	action def VerifyAssembly {
		in assembledStructure : AssembledProduct;
		in targetStructure : TargetStructure;
		out verified : Boolean;
		out defects : Integer;
		out qualityScore : Real;
	}
	
	action def AssembleMolecularStructure {
		doc /* Primary assembly process coordinating all subsystems */
		
		in targetStructure : TargetStructure;
		in feedstock : Feedstock;
		in powerSupply : PowerValue;
		out assembledProduct : AssembledProduct;
		
		private attribute currentAtomIndex : Integer := 0;
		private attribute totalAtoms : Integer;
		private attribute currentStructure : AssembledProduct;
		private attribute assemblyErrors : Integer := 0;
		
		first start;
		then merge initialize;
		
		then action initializeAssembly {
			assign totalAtoms := 10;
			assign currentStructure := AssembledProduct {
				defectCount = 0;
				qualityScore = 1.0;
			}
		}
		
		then merge assemblyLoop;
		
		then decide;
			if currentAtomIndex < totalAtoms then selectNextAtom;
			if currentAtomIndex >= totalAtoms then verifyFinal;
		
		action selectNextAtom : SelectAtom {
			in feedstock = AssembleMolecularStructure::feedstock;
			in requiredType;
			out selectedAtom;
			out remainingFeedstock;
		}
		
		then action positionSelectedAtom : PositionAtomPrecisely {
			in atom = selectNextAtom.selectedAtom;
			in targetPosition;
			in precision;
			out positionedAtom;
			out positionError;
		}
		
		then decide;
			if positionSelectedAtom.positionError <= 0.1 [nm] then checkBonding;
			if positionSelectedAtom.positionError > 0.1 [nm] then handlePositioningError;
		
		action handlePositioningError {
			assign assemblyErrors := assemblyErrors + 1;
		}
		then decide;
			if assemblyErrors < 3 then assemblyLoop;
			if assemblyErrors >= 3 then abortAssembly;
		
		action checkBonding {
			then decide;
				if currentAtomIndex > 0 then formBondAction;
				if currentAtomIndex == 0 then updateProgress;
		}
		
		action formBondAction : FormChemicalBond {
			in atom1 = positionSelectedAtom.positionedAtom;
			in atom2;
			in bondType;
			in bondingEnergy;
			out bondFormed;
			out bondStrength;
		}
		
		then decide;
			if formBondAction.bondFormed then updateProgress;
			if not formBondAction.bondFormed then handleBondingError;
		
		action handleBondingError {
			assign assemblyErrors := assemblyErrors + 1;
		}
		then decide;
			if assemblyErrors < 3 then assemblyLoop;
			if assemblyErrors >= 3 then abortAssembly;
		
		action updateProgress {
			assign currentAtomIndex := currentAtomIndex + 1;
		}
		then assemblyLoop;
		
		action verifyFinal : VerifyAssembly {
			in assembledStructure = currentStructure;
			in targetStructure = AssembleMolecularStructure::targetStructure;
			out verified;
			out defects;
			out qualityScore;
		}
		
		then decide;
			if verifyFinal.verified and verifyFinal.qualityScore >= 0.95 then completeAssembly;
			if not verifyFinal.verified or verifyFinal.qualityScore < 0.95 then correctDefects;
		
		action correctDefects {
			doc /* Attempt to repair detected defects */
		}
		then decide;
			if assemblyErrors < 5 then assemblyLoop;
			if assemblyErrors >= 5 then abortAssembly;
		
		action completeAssembly {
			assign assembledProduct := currentStructure;
		}
		then done;
		
		action abortAssembly {
			assign assembledProduct := AssembledProduct {
				defectCount = assemblyErrors;
				qualityScore = 0.0;
			}
		}
		then done;
	}
	
	part def MolecularAssembler {
		doc /* Complete molecular assembler system for atom-by-atom construction of complex molecular structures */
		
		attribute operationalPrecision : AtomicPrecision;
		attribute maxAssemblyRate : AssemblyRate;
		attribute energyEfficiency : Real;
		attribute chamberTemperature : ThermodynamicTemperatureValue;
		
		port feedstockInput : FeedstockPort;
		port productOutput : ProductPort;
		port controlInterface : ControlPort;
		port powerInput : PowerPort;
		
		part feedstockProcessor : FeedstockProcessor {
			port feedstockIn = molecularAssembler::feedstockInput;
		}
		
		part assemblyController : AssemblyController {
			port controlOut = molecularAssembler::controlInterface;
		}
		
		part atomicManipulator : AtomicManipulator {
			port controlIn;
			port powerIn = molecularAssembler::powerInput;
		}
		
		part bondingUnit : BondingUnit;
		
		part verificationScanner : VerificationScanner;
		
		connection feedstockFlow connect 
			feedstockProcessor::feedstockIn to atomicManipulator::controlIn;
		
		connection controlFlow connect 
			assemblyController::controlOut to atomicManipulator::controlIn;
		
		connection powerFlow connect 
			molecularAssembler::powerInput to atomicManipulator::powerIn;
		
		perform action assembleMolecularStructure : AssembleMolecularStructure {
			in targetStructure;
			in feedstock;
			in powerSupply;
			out assembledProduct;
		}
	}
	
	part molecularAssembler : MolecularAssembler;
	
	requirement def PrecisionRequirement {
		doc /* Atomic positioning must achieve sub-nanometer precision */
		
		subject assembler : MolecularAssembler;
		
		require constraint {
			assembler.operationalPrecision <= 0.1 [nm]
		}
	}
	
	requirement def AssemblyRateRequirement {
		doc /* System must position minimum number of atoms per second */
		
		subject assembler : MolecularAssembler;
		
		require constraint {
			assembler.maxAssemblyRate >= 1000000.0
		}
	}
	
	requirement def QualityRequirement {
		doc /* Assembled products must meet minimum quality standards */
		
		subject product : AssembledProduct;
		
		require constraint {
			product.qualityScore >= 0.95 and product.defectCount <= 5
		}
	}
	
	requirement def EnergyEfficiencyRequirement {
		doc /* Assembly process must maintain high energy efficiency */
		
		subject assembler : MolecularAssembler;
		
		require constraint {
			assembler.energyEfficiency >= 0.85
		}
	}
	
	requirement def TemperatureControlRequirement {
		doc /* Assembly chamber must maintain stable temperature */
		
		subject assembler : MolecularAssembler;
		
		require constraint {
			assembler.chamberTemperature >= 295.0 [K] and 
			assembler.chamberTemperature <= 310.0 [K]
		}
	}
	
	requirement <'MA-001'> molecularAssemblerMission {
		doc /* The molecular assembler shall construct complex molecular structures 
		       through precise atom-by-atom assembly from atomic feedstock according 
		       to a digital blueprint, achieving sub-nanometer positioning accuracy 
		       and producing high-quality products with minimal defects. */
		
		subject assembler : MolecularAssembler;
		
		assume constraint feedstockAvailability {
			doc /* Sufficient purified atomic feedstock is available for assembly */
		}
		
		assume constraint environmentalControl {
			doc /* Assembly occurs in controlled vacuum or inert atmosphere */
		}
		
		assume constraint powerAvailability {
			doc /* Adequate power supply is available for assembly operations */
		}
		
		require precisionReq : PrecisionRequirement;
		require rateReq : AssemblyRateRequirement;
		require qualityReq : QualityRequirement;
		require efficiencyReq : EnergyEfficiencyRequirement;
		require temperatureReq : TemperatureControlRequirement;
	}
}

// --- Test harness (auto-generated) ---
package ExecutionHarness {
    private import ScalarValues::*;
    private import ISQ::*;
    private import SI::*;
    private import 'Molecular Assembler System'::*;

    action orchestrator {
        attribute testRequiredType : AtomType;
        action selectNextAtomProbe : SelectAtom {
            // TODO(human): unsupported input type for feedstock: Feedstock (unsupported structured payload members: availableAtoms)
            in requiredType = testRequiredType;
        }
        first selectNextAtomProbe;
    }
}

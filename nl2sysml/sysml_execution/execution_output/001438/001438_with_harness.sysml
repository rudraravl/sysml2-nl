package GynoidDomesticAssistantSystem {
    private import ScalarValues::*;
    private import ISQ::*;
    private import SI::*;
    
    attribute def TaskIdentifier;
    attribute def EnvironmentMap {
        attribute taskAvailable : Boolean;
    }
    attribute def ObjectIdentifier;
    attribute def VoiceCommand;
    attribute def NavigationPath;
    attribute def GripConfiguration;
    
    item def ElectricalEnergy {
        attribute voltage : ElectricPotentialValue;
        attribute current : ElectricCurrentValue;
        attribute power : PowerValue;
    }
    
    item def MotorCommand {
        attribute targetAngle : DimensionlessValue;
        attribute targetTorque : TorqueValue;
        attribute targetVelocity : AngularVelocityValue;
    }
    
    item def SensorReading {
        attribute timestamp : TimeValue;
        attribute dataType : String;
        attribute value : Real;
    }
    
    item def VisualData {
        attribute imageResolution : Integer;
        attribute depthData : LengthValue[*];
        attribute objectsDetected : ObjectIdentifier[*];
    }
    
    item def AudioData {
        attribute sampleRate : FrequencyValue;
        attribute amplitude : Real;
        attribute recognizedCommand : VoiceCommand;
    }
    
    port def PowerPort {
        in item energySupply : ElectricalEnergy;
    }
    
    port def DataPort {
        in item inputData : SensorReading;
        out item outputData : SensorReading;
    }
    
    port def MotorControlPort {
        in item command : MotorCommand;
        out item feedback : DimensionlessValue;
    }
    
    port def SensorPort {
        out item reading : SensorReading;
    }
    
    port def CommunicationPort {
        in item userCommand : VoiceCommand;
        out item systemResponse : String;
    }
    
    part def BatterySystem {
        port powerOutput : ~PowerPort;
        attribute capacity : EnergyValue;
        attribute currentCharge : EnergyValue;
        attribute chargingRate : PowerValue;
        attribute dischargingRate : PowerValue;
        
        action monitorBattery {
            in currentLoad : PowerValue;
            out chargeLevel : Real;
            out timeRemaining : TimeValue;
        }
    }
    
    part def VisionSubsystem {
        port visionPower : PowerPort;
        port visionData : ~DataPort;
        
        part stereoCameras[2] {
            attribute resolution : Integer;
            attribute fieldOfView : DimensionlessValue;
        }
        
        part depthSensor {
            attribute range : LengthValue;
            attribute accuracy : LengthValue;
        }
        
        part imageProcessor {
            action processVisualInput {
                in rawImages : VisualData;
                out processedScene : EnvironmentMap;
                out detectedObjects : ObjectIdentifier[*];
            }
        }
    }
    
    part def AudioSubsystem {
        port audioPower : PowerPort;
        port audioData : ~DataPort;
        port communication : ~CommunicationPort;
        
        part microphoneArray[4] {
            attribute sensitivity : Real;
            attribute frequency : FrequencyValue;
        }
        
        part speaker[2] {
            attribute outputPower : PowerValue;
            attribute frequencyRange : FrequencyValue;
        }
        
        part speechProcessor {
            action recognizeSpeech {
                in audioInput : AudioData;
                out command : VoiceCommand;
                out confidence : Real;
            }
            
            action synthesizeSpeech {
                in textResponse : String;
                out audioOutput : AudioData;
            }
        }
    }
    
    part def LocomotionSystem {
        port locomotionPower : PowerPort;
        port locomotionControl : MotorControlPort;
        
        part legs[2] {
            part hip {
                part motors[3] {
                    attribute maxTorque : TorqueValue;
                    attribute maxSpeed : AngularVelocityValue;
                }
            }
            
            part knee {
                part motor {
                    attribute maxTorque : TorqueValue;
                }
            }
            
            part ankle {
                part motors[2] {
                    attribute maxTorque : TorqueValue;
                }
            }
            
            part footSensor {
                attribute forceRange : ForceValue;
            }
        }
        
        action executeWalk {
            in targetPosition : LengthValue[3];
            in currentPosition : LengthValue[3];
            out legCommands : MotorCommand[*];
        }
    }
    
    part def ManipulationSystem {
        port manipulationPower : PowerPort;
        port manipulationControl : MotorControlPort;
        
        part arms[2] {
            part shoulder {
                part motors[3] {
                    attribute maxTorque : TorqueValue;
                }
            }
            
            part elbow {
                part motor {
                    attribute maxTorque : TorqueValue;
                }
            }
            
            part wrist {
                part motors[2] {
                    attribute maxTorque : TorqueValue;
                }
            }
            
            part hand {
                part fingers[5] {
                    part joints[3] {
                        part motor {
                            attribute maxTorque : TorqueValue;
                        }
                    }
                }
                
                part tactileSensors[20] {
                    attribute pressureRange : PressureValue;
                }
            }
        }
        
        action executeGrasp {
            in targetObject : ObjectIdentifier;
            in graspType : GripConfiguration;
            out handCommands : MotorCommand[*];
        }
        
        action executeReach {
            in targetPosition : LengthValue[3];
            out armCommands : MotorCommand[*];
        }
    }
    
    part def BalanceController {
        port balancePower : PowerPort;
        port balanceSensors : SensorPort;
        
        part imu {
            part gyroscope {
                attribute range : AngularVelocityValue;
            }
            
            part accelerometer {
                attribute range : AccelerationValue;
            }
        }
        
        action maintainStability {
            in sensorData : SensorReading[*];
            in currentPosture : DimensionlessValue[*];
            out stabilizationCommands : MotorCommand[*];
        }
    }
    
    part def CognitiveCore {
        port cognitivePower : PowerPort;
        port cognitiveData : DataPort;
        
        attribute processingCapacity : Real;
        attribute memorySize : Real;
        
        action perceiveEnvironment {
            in visualInput : VisualData;
            in audioInput : AudioData;
            in tactileInput : SensorReading[*];
            out worldModel : EnvironmentMap;
        }
        
        action planTask {
            in taskGoal : TaskIdentifier;
            in worldModel : EnvironmentMap;
            out actionSequence : String[*];
            out navigationPlan : NavigationPath;
        }
        
        action makeDecision {
            in currentState : EnvironmentMap;
            in userIntent : VoiceCommand;
            out selectedTask : TaskIdentifier;
            out priority : Real;
        }
        
        action coordinateActions {
            in actionPlan : String[*];
            out locomotionCommands : MotorCommand[*];
            out manipulationCommands : MotorCommand[*];
            out verbalResponse : String;
        }
    }
    
    part gynoid {
        doc /* Humanoid robotic assistant designed for domestic task execution and human interaction. */
        
        attribute height : LengthValue;
        attribute mass : MassValue;
        attribute operatingTemperature : ThermodynamicTemperatureValue;
        
        port externalPower : PowerPort;
        port userInterface : CommunicationPort;
        
        part battery : BatterySystem {
            :>> capacity = 10000.0 [J];
            :>> currentCharge = 8000.0 [J];
        }
        
        part brain : CognitiveCore {
            :>> processingCapacity = 100.0;
            :>> memorySize = 2000.0;
        }
        
        part vision : VisionSubsystem;
        part audio : AudioSubsystem;
        part locomotion : LocomotionSystem;
        part manipulation : ManipulationSystem;
        part balance : BalanceController;
        
        connection batteryToBrain connect battery.powerOutput to brain.cognitivePower;
        connection batteryToVision connect battery.powerOutput to vision.visionPower;
        connection batteryToAudio connect battery.powerOutput to audio.audioPower;
        connection batteryToLocomotion connect battery.powerOutput to locomotion.locomotionPower;
        connection batteryToManipulation connect battery.powerOutput to manipulation.manipulationPower;
        connection batteryToBalance connect battery.powerOutput to balance.balancePower;
        
        connection visionToBrain connect vision.visionData to brain.cognitiveData;
        connection audioToBrain connect audio.audioData to brain.cognitiveData;
        connection audioToUser connect audio.communication to userInterface;
        
        perform action assistHumans;
    }
    
    action def PerformDomesticTask {
        in taskRequest : VoiceCommand;
        in environmentState : EnvironmentMap;
        out taskCompletion : Boolean;
        out statusReport : String;
    }
    
    action def NavigateToLocation {
        in targetLocation : LengthValue[3];
        in obstacleMap : EnvironmentMap;
        out path : NavigationPath;
        out movementCommands : MotorCommand[*];
    }
    
    action def ManipulateObject {
        in objectId : ObjectIdentifier;
        in manipulationType : String;
        out graspSuccess : Boolean;
        out objectPosition : LengthValue[3];
    }
    
    action def InteractWithHuman {
        in userPresence : Boolean;
        in userSpeech : VoiceCommand;
        out verbalResponse : String;
        out taskAcknowledgment : Boolean;
    }
    
    action assistHumans {
        doc /* Primary operational behavior for domestic assistance. */
        
        first start;
        then merge operationalLoop;
        
        action sense {
            action captureVisual {
                out visualScene : VisualData;
            }
            
            action listenForCommands {
                out audioInput : AudioData;
            }
            
            action readSensors {
                out tactileData : SensorReading[*];
                out balanceData : SensorReading[*];
            }
            
            then action buildWorldModel {
                in visual = captureVisual.visualScene;
                in audio = listenForCommands.audioInput;
                in tactile = readSensors.tactileData;
                out environmentModel : EnvironmentMap;
            }
        }
        
        then decide;
            if sense.listenForCommands.audioInput.recognizedCommand != null then processCommand;
            if sense.buildWorldModel.environmentModel.taskAvailable then executeTask;
            else maintainReadiness;
        
        action processCommand : InteractWithHuman {
            action interpretCommand {
                in userCommand : VoiceCommand;
                out taskType : TaskIdentifier;
                out parameters : String[*];
            }
            
            then action acknowledgeUser {
                in task = interpretCommand.taskType;
                out response : String;
            }
            
            then action initiateTask {
                in taskId = interpretCommand.taskType;
                in params = interpretCommand.parameters;
                out taskStarted : Boolean;
            }
        }
        then operationalLoop;
        
        action executeTask : PerformDomesticTask {
            action planExecution {
                in task : TaskIdentifier;
                in environment : EnvironmentMap;
                out steps : String[*];
            }
            
            then action performSteps {
                action navigateToTarget : NavigateToLocation {
                    in targetLocation : LengthValue[3];
                    in obstacleMap : EnvironmentMap;
                    out path : NavigationPath;
                }
                
                then action manipulateTarget : ManipulateObject {
                    in objectId : ObjectIdentifier;
                    in manipulationType : String;
                    out graspSuccess : Boolean;
                }
                
                then action returnToBase : NavigateToLocation {
                    in targetLocation : LengthValue[3];
                    in obstacleMap : EnvironmentMap;
                    out path : NavigationPath;
                }
            }
            
            then action reportCompletion {
                in success : Boolean;
                out statusMessage : String;
            }
        }
        then operationalLoop;
        
        action maintainReadiness {
            action monitorEnvironment {
                out changes : EnvironmentMap;
            }
            
            action conservePower {
                out powerMode : String;
            }
            
            action maintainPosture {
                out balanceCommands : MotorCommand[*];
            }
        }
        then operationalLoop;
    }
    
    requirement def PrimaryFunctionRequirement {
        doc /* The gynoid shall autonomously assist humans with domestic tasks through perception, planning, and physical interaction. */
        
        subject gynoid;
        
        require constraint perceptionCapability {
            doc /* The gynoid shall perceive its environment using vision, audio, and tactile sensors. */
        }
        
        require constraint taskPlanningCapability {
            doc /* The gynoid shall plan and execute multi-step domestic tasks autonomously. */
        }
        
        require constraint humanInteractionCapability {
            doc /* The gynoid shall interact naturally with humans through speech and gesture. */
        }
    }
    
    requirement def SafetyRequirement {
        doc /* The gynoid shall operate safely in human-occupied environments. */
        
        require constraint forceLimit {
            doc /* Maximum applied force shall not exceed 50N in normal operation. */
        }
        
        require constraint collisionAvoidance {
            doc /* The gynoid shall detect and avoid collisions with humans and objects. */
        }
        
        require constraint emergencyStop {
            doc /* The gynoid shall respond to emergency stop commands within 100ms. */
        }
    }
    
    requirement def PerformanceRequirement {
        doc /* The gynoid shall meet specified performance criteria. */
        
        require constraint batteryEndurance {
            doc /* The gynoid shall operate continuously for at least 6 hours on a single charge. */
        }
        
        require constraint taskCompletionRate {
            doc /* The gynoid shall successfully complete at least 90% of assigned tasks. */
        }
        
        require constraint responseTime {
            doc /* The gynoid shall respond to user commands within 2 seconds. */
        }
        
        require constraint navigationAccuracy {
            doc /* The gynoid shall navigate to target locations with accuracy within 5cm. */
        }
    }
    
    requirement def MobilityRequirement {
        doc /* The gynoid shall demonstrate human-like mobility and manipulation. */
        
        require constraint walkingSpeed {
            doc /* The gynoid shall walk at speeds up to 1.5 m/s. */
        }
        
        require constraint reachRange {
            doc /* Arm reach shall be at least 0.8m from shoulder joint. */
        }
        
        require constraint graspPrecision {
            doc /* The gynoid shall grasp objects with position accuracy within 2mm. */
        }
        
        require constraint balanceStability {
            doc /* The gynoid shall maintain balance during manipulation tasks. */
        }
    }
    
    requirement gynoidSystemRequirements {
        doc /* Top-level requirements for the gynoid domestic assistant system. */
        
        require req1 : PrimaryFunctionRequirement;
        require req2 : SafetyRequirement;
        require req3 : PerformanceRequirement;
        require req4 : MobilityRequirement;
        
        satisfy req1 by gynoid.assistHumans;
    }
}

// --- Test harness (auto-generated) ---
package ExecutionHarness {
    private import ScalarValues::*;
    private import ISQ::*;
    private import SI::*;
    private import GynoidDomesticAssistantSystem::*;

    action orchestrator {
        attribute testUserSpeech : VoiceCommand;
        action processCommandProbe : InteractWithHuman {
            in userPresence = false;
            in userSpeech = testUserSpeech;
        }
        first processCommandProbe;
    }
}

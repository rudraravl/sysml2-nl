package 'Holodeck Simulation System' {
	private import ScalarValues::*;
	private import ISQ::*;
	
	attribute def ResolutionLevel :> Real;
	attribute def ProcessingLoad :> Real;
	attribute def SafetyProtocolStatus :> Boolean;
	attribute def SimulationFidelity :> Real;
	attribute def HapticIntensity :> Real;
	
	item def PhotonicEnergy;
	item def ForceFieldMatrix;
	item def MatterStream;
	item def SensorData;
	
	attribute def ProgramParameters {
		attribute scenarioID : String;
		attribute environmentType : String;
		attribute participantCount : Integer;
		attribute difficultyLevel : Real;
		attribute safetyMode : Boolean;
	}
	
	attribute def EnvironmentState {
		attribute spatialResolution : ResolutionLevel;
		attribute temporalCoherence : Real;
		attribute physicalRealism : SimulationFidelity;
		attribute interactionLatency : DurationValue;
	}
	
	port def PhotonicInput {
		in item photons : PhotonicEnergy;
	}
	
	port def PhotonicOutput {
		out item photons : PhotonicEnergy;
	}
	
	port def ForceFieldInput {
		in item field : ForceFieldMatrix;
	}
	
	port def ForceFieldOutput {
		out item field : ForceFieldMatrix;
	}
	
	port def MatterInput {
		in item matter : MatterStream;
	}
	
	port def MatterOutput {
		out item matter : MatterStream;
	}
	
	port def ControlInterface {
		in attribute programParams : ProgramParameters;
		out attribute envState : EnvironmentState;
		out attribute systemStatus : Real;
	}
	
	port def SensorInterface {
		in item sensorInput : SensorData;
		out attribute trackingData : Real;
	}
	
	part def HolographicProjector {
		attribute projectorID : Integer;
		attribute emitterCount : Integer;
		attribute wavelengthRange : LengthValue;
		attribute maxLuminosity : LuminousIntensityValue;
		
		port photonicOut : PhotonicOutput;
		port controlIn : ControlInterface;
		
		action def ProjectHologram {
			in params : ProgramParameters;
			in spatialCoordinates : Real[3];
			out holographicImage : PhotonicEnergy;
			out imageQuality : ResolutionLevel;
		}
		
		action def ModulateIntensity {
			in targetBrightness : Real;
			in currentOutput : Real;
			out adjustedOutput : PhotonicEnergy;
		}
	}
	
	part def ForceFieldEmitter {
		attribute emitterID : Integer;
		attribute fieldStrength : Real;
		attribute responseTime : DurationValue;
		attribute coverageArea : AreaValue;
		
		port fieldOut : ForceFieldOutput;
		port controlIn : ControlInterface;
		
		action def GenerateForceField {
			in fieldGeometry : Real[3];
			in resistanceLevel : Real;
			out forceField : ForceFieldMatrix;
			out fieldIntegrity : Real;
		}
		
		action def AdjustFieldProperties {
			in targetDensity : Real;
			in targetElasticity : Real;
			out modifiedField : ForceFieldMatrix;
		}
	}
	
	part def MatterReplicator {
		attribute replicatorID : Integer;
		attribute molecularResolution : LengthValue;
		attribute maxMassRate : MassValue;
		attribute patternBufferCapacity : Real;
		
		port matterOut : MatterOutput;
		port controlIn : ControlInterface;
		
		action def SynthesizeMatter {
			in molecularPattern : Real;
			in quantity : MassValue;
			out replicatedMatter : MatterStream;
			out synthesisAccuracy : Real;
		}
		
		action def RecycleMatter {
			in usedMatter : MatterStream;
			out energyRecovered : EnergyValue;
		}
	}
	
	part def SpatialSensor {
		attribute sensorID : Integer;
		attribute scanResolution : LengthValue;
		attribute updateFrequency : FrequencyValue;
		attribute trackingAccuracy : Real;
		
		port sensorPort : SensorInterface;
		
		action def TrackParticipants {
			in scanArea : AreaValue;
			out participantPositions : Real[*];
			out participantVelocities : Real[*];
		}
		
		action def DetectInteractions {
			in objectPositions : Real[*];
			out collisionEvents : Real[*];
			out proximityData : Real[*];
		}
	}
	
	part def SimulationProcessor {
		attribute processorID : Integer;
		attribute computePower : Real;
		attribute memoryCapacity : Real;
		attribute parallelThreads : Integer;
		
		port controlPort : ControlInterface;
		port sensorInput : SensorInterface;
		
		action def LoadProgram {
			in programParams : ProgramParameters;
			out programState : EnvironmentState;
			out loadSuccess : Boolean;
		}
		
		action def UpdateSimulation {
			in currentState : EnvironmentState;
			in sensorData : SensorData;
			in deltaTime : DurationValue;
			out newState : EnvironmentState;
			out renderCommands : Real[*];
		}
		
		action def CalculatePhysics {
			in objectStates : Real[*];
			in forces : Real[*];
			out updatedStates : Real[*];
			out interactions : Real[*];
		}
		
		action def MonitorSafety {
			in participantData : Real[*];
			in environmentData : EnvironmentState;
			out safetyStatus : SafetyProtocolStatus;
			out emergencyShutdown : Boolean;
		}
	}
	
	part def SafetyInterlock {
		attribute interlockID : Integer;
		attribute responseThreshold : Real;
		attribute emergencyPowerReserve : EnergyValue;
		
		port controlPort : ControlInterface;
		
		action def EnforceSafetyLimits {
			in currentLoad : ProcessingLoad;
			in participantStress : Real;
			out limitationActive : Boolean;
			out powerReduction : Real;
		}
		
		action def InitiateEmergencyShutdown {
			out shutdownComplete : Boolean;
			out participantsSafe : Boolean;
		}
	}
	
	part holodeckSystem {
		attribute gridID : String;
		attribute operationalMode : String;
		
		part processor : SimulationProcessor {
			:>> processorID = 1;
			:>> parallelThreads = 256;
		}
		
		part projectorArray : HolographicProjector[144] {
			:>> emitterCount = 1024;
		}
		
		part forceFieldGrid : ForceFieldEmitter[96] {
			:>> responseTime = 0.001 [SI::s];
		}
		
		part replicatorUnits : MatterReplicator[24] {
			:>> maxMassRate = 10.0 [SI::kg];
		}
		
		part spatialSensors : SpatialSensor[48] {
			:>> updateFrequency = 1000.0 [SI::Hz];
		}
		
		part safetySystem : SafetyInterlock {
			:>> interlockID = 1;
		}
		
		port userInterface : ControlInterface;
		
		connect processor.controlPort to userInterface;
		connect processor.sensorInput to spatialSensors[1].sensorPort;
		connect processor.controlPort to safetySystem.controlPort;
		
		connect projectorArray[1].controlIn to processor.controlPort;
		connect forceFieldGrid[1].controlIn to processor.controlPort;
		connect replicatorUnits[1].controlIn to processor.controlPort;
		
		perform action runSimulation;
	}
	
	action def InitializeHolodeck {
		in programParams : ProgramParameters;
		out systemReady : Boolean;
		out initialState : EnvironmentState;
	}
	
	action def ActivateProjectors {
		in renderData : Real[*];
		out projectorsActive : Boolean;
	}
	
	action def ActivateForceFields {
		in fieldConfiguration : Real[*];
		out fieldsActive : Boolean;
	}
	
	action def ReplicateEnvironment {
		in objectList : Real[*];
		out objectsCreated : Boolean;
	}
	
	action def MonitorParticipants {
		in sensorData : SensorData;
		out participantStatus : Real[*];
	}
	
	action def UpdateEnvironmentAction {
		in currentState : EnvironmentState;
		in participantActions : Real[*];
		in deltaTime : DurationValue;
		out newState : EnvironmentState;
	}
	
	action def CheckSafety {
		in environmentState : EnvironmentState;
		in participantData : Real[*];
		out safetyOK : Boolean;
	}
	
	action def TerminateSimulation {
		out simulationEnded : Boolean;
		out resourcesReleased : Boolean;
	}
	
	action runSimulation {
		first start;
		
		then action initialize : InitializeHolodeck {
			in programParams : ProgramParameters;
			out systemReady;
			out initialState;
		}
		
		then decide;
			if initialize.systemReady then proceedToActivation;
			if !initialize.systemReady then abortSim;
		
		action proceedToActivation {
			action activateProj : ActivateProjectors {
				in renderData : Real[*];
				out projectorsActive;
			}
			
			then action activateFields : ActivateForceFields {
				in fieldConfiguration : Real[*];
				out fieldsActive;
			}
			
			then action replicateEnv : ReplicateEnvironment {
				in objectList : Real[*];
				out objectsCreated;
			}
		}
		
		then merge simulationLoop;
		
		loop {
			action monitor : MonitorParticipants {
				in sensorData : SensorData;
				out participantStatus;
			}
			
			then action update : UpdateEnvironmentAction {
				in currentState : EnvironmentState;
				in participantActions = monitor.participantStatus;
				in deltaTime : DurationValue;
				out newState;
			}
			
			then action safety : CheckSafety {
				in environmentState = update.newState;
				in participantData = monitor.participantStatus;
				out safetyOK;
			}
			
			then decide;
				if safety.safetyOK then continueSimulation;
				if !safety.safetyOK then emergencyStop;
			
			merge continueSimulation;
			
			then accept endCommand;
			
			then action terminate : TerminateSimulation {
				out simulationEnded;
				out resourcesReleased;
			}
		}
		then simulationLoop;
		
		action emergencyStop : TerminateSimulation {
			out simulationEnded;
			out resourcesReleased;
		}
		then simulationLoop;
		
		action abortSim : TerminateSimulation {
			out simulationEnded;
			out resourcesReleased;
		}
		
		then done;
	}
	
	requirement def HolodeckRequirements {
		doc /* The holodeck system shall create immersive, interactive simulated 
		       environments using holographic projection, force fields, and matter 
		       replication technology. */
		
		requirement immersionCapability {
			doc /* The system shall achieve visual resolution indistinguishable from 
			       reality at normal viewing distances. */
			
			require constraint { 
				holodeckSystem.processor.controlPort.envState.spatialResolution >= 0.99 
			}
		}
		
		requirement physicalInteraction {
			doc /* Force fields shall provide tactile feedback with response time 
			       under 2 milliseconds. */
			
			require constraint { 
				holodeckSystem.forceFieldGrid[1].responseTime < 0.002 [SI::s] 
			}
		}
		
		requirement participantSafety {
			doc /* Safety interlocks shall prevent participant injury by monitoring 
			       stress levels and environmental hazards continuously. */
			
			require constraint { 
				holodeckSystem.safetySystem.responseThreshold < 0.95 
			}
		}
		
		requirement simulationFidelity {
			doc /* Physical simulations shall maintain temporal coherence above 95% 
			       for realistic interaction dynamics. */
			
			require constraint { 
				holodeckSystem.processor.controlPort.envState.temporalCoherence >= 0.95 
			}
		}
		
		requirement interactionLatency {
			doc /* System response to participant actions shall occur within 10 
			       milliseconds to maintain immersion. */
			
			require constraint { 
				holodeckSystem.processor.controlPort.envState.interactionLatency < 0.01 [SI::s] 
			}
		}
		
		requirement resourceEfficiency {
			doc /* Matter replication shall recycle unused materials

// --- Test harness (auto-generated) ---
package ExecutionHarness {
    private import ScalarValues::*;
    private import ISQ::*;
    private import 'Holodeck Simulation System'::*;

    action orchestrator {
        action activateProjProbe : ActivateProjectors {
            // TODO(human): unsupported input type for renderData: Real[*] (type is not a primitive, enum, extracted payload def, or known value type)
        }
        first activateProjProbe;
    }
}

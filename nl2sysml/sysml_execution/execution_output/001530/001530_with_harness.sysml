package PicotechnologyNanoManipulationSystem {
    private import ScalarValues::*;
    private import ISQ::*;
    private import SI::*;
    
    attribute def PicometerLength :> LengthValue {
        doc /* Length measurements at picometer scale (10^-12 meters) */
    }
    
    attribute def FemtonewtonForce :> ForceValue {
        doc /* Force measurements at femtonewton scale (10^-15 newtons) */
    }
    
    attribute def AttojouleEnergy :> EnergyValue {
        doc /* Energy measurements at attojoule scale (10^-18 joules) */
    }
    
    attribute def NanometerDisplacement :> LengthValue {
        doc /* Displacement range in nanometers */
    }
    
    attribute def PicosecondDuration :> TimeValue {
        doc /* Time measurements at picosecond scale */
    }
    
    attribute def SpatialCoordinate {
        attribute x : PicometerLength;
        attribute y : PicometerLength;
        attribute z : PicometerLength;
    }
    
    enum def MoleculeType {
        carbon;
        silicon;
        hydrogen;
        oxygen;
        nitrogen;
        custom;
    }
    
    item def AtomicTarget {
        attribute position : SpatialCoordinate;
        attribute moleculeType : MoleculeType;
        attribute bondingEnergy : AttojouleEnergy;
    }
    
    item def ManipulationSequence {
        attribute targetAtoms : AtomicTarget[*] ordered;
        attribute assemblyPattern : SpatialCoordinate[*] ordered;
        attribute bondingSequence : Integer[*] ordered;
    }
    
    item def AssembledStructure {
        attribute finalConfiguration : SpatialCoordinate[*];
        attribute structureIntegrity : Real;
        ref sourceSequence : ManipulationSequence;
    }
    
    port def ProbeControlPort {
        in attribute targetPosition : SpatialCoordinate;
        in attribute approachForce : FemtonewtonForce;
        out attribute actualPosition : SpatialCoordinate;
        out attribute tunnelingCurrent : ElectricCurrentValue;
    }
    
    port def ImagingPort {
        in attribute scanArea : NanometerDisplacement;
        in attribute scanResolution : PicometerLength;
        out attribute surfaceTopography : SpatialCoordinate[*];
        out attribute atomicMap : AtomicTarget[*];
    }
    
    port def VacuumControlPort {
        in attribute targetPressure : PressureValue;
        out attribute actualPressure : PressureValue;
        out attribute chamberTemperature : TemperatureValue;
    }
    
    port def FeedbackPort {
        in attribute sensorData : Real[*];
        out attribute correctionSignal : Real;
    }
    
    part def ScanningProbe {
        doc /* Ultra-sharp probe for atomic-scale manipulation */
        attribute tipRadius : PicometerLength;
        attribute resonanceFrequency : FrequencyValue;
        
        port probeControl : ProbeControlPort;
        
        part probeTip {
            attribute sharpness : Real;
            attribute material : String;
        }
        
        part piezoActuator {
            attribute displacement : NanometerDisplacement;
            attribute responseTime : PicosecondDuration;
        }
    }
    
    part def AtomicForceController {
        doc /* Precision force control for atomic manipulation */
        attribute forceSetpoint : FemtonewtonForce;
        attribute controlBandwidth : FrequencyValue;
        
        port feedbackIn : FeedbackPort;
        port commandOut : ProbeControlPort;
    }
    
    part def HighResolutionImager {
        doc /* Atomic-resolution imaging system */
        attribute imagingResolution : PicometerLength;
        attribute scanSpeed : Real;
        
        port imagingControl : ImagingPort;
        
        part detector {
            attribute sensitivity : Real;
            attribute noiseFloor : ElectricCurrentValue;
        }
    }
    
    part def UltraHighVacuumChamber {
        doc /* Environmental control chamber */
        attribute baselinePressure : PressureValue;
        attribute operatingTemperature : TemperatureValue;
        
        port vacuumControl : VacuumControlPort;
        
        part pumpingSystem {
            attribute pumpingSpeed : Real;
        }
        
        part thermalStabilizer {
            attribute stabilityRange : TemperatureValue;
        }
    }
    
    part def PositionFeedbackSystem {
        doc /* Real-time position monitoring and correction */
        attribute measurementAccuracy : PicometerLength;
        attribute updateRate : FrequencyValue;
        
        port sensorInput : FeedbackPort;
    }
    
    part def AtomicReservoir {
        doc /* Source of atoms for assembly */
        attribute availableTypes : MoleculeType[*];
        attribute atomSupplyRate : Real;
        
        port dispensingPort {
            out attribute dispensedAtom : AtomicTarget;
        }
    }
    
    action def InitializeSystem {
        doc /* Prepare system for atomic manipulation */
        out attribute systemReady : Boolean;
        
        first start;
        then action evacuateChamber {
            out attribute vacuumAchieved : Boolean;
        }
        then action stabilizeTemperature {
            out attribute temperatureStable : Boolean;
        }
        then action calibrateProbe {
            out attribute probeCalibrated : Boolean;
        }
        then decide;
            if evacuateChamber.vacuumAchieved and 
               stabilizeTemperature.temperatureStable and 
               calibrateProbe.probeCalibrated 
            then setReady;
            else failInitialization;
        
        action setReady {
            out attribute systemReady = true;
        }
        then done;
        
        action failInitialization {
            out attribute systemReady = false;
        }
        then done;
    }
    
    action def ScanTargetArea {
        doc /* Scan surface to identify atomic targets */
        in attribute scanRegion : NanometerDisplacement;
        in attribute resolution : PicometerLength;
        out attribute detectedAtoms : AtomicTarget[*];
        
        first start;
        then action configureScan {
            in attribute area = scanRegion;
            in attribute res = resolution;
        }
        then action performRasterScan {
            out attribute rawTopography : SpatialCoordinate[*];
        }
        then action identifyAtoms {
            in attribute topographyData = performRasterScan.rawTopography;
            out attribute atomicTargets : AtomicTarget[*];
        }
        then assign detectedAtoms := identifyAtoms.atomicTargets;
        then done;
    }
    
    action def ApproachAtom {
        doc /* Precisely approach target atom */
        in attribute targetAtom : AtomicTarget;
        in attribute approachSpeed : Real;
        out attribute contactEstablished : Boolean;
        
        private attribute currentDistance : PicometerLength;
        private attribute tunnelingDetected : Boolean := false;
        
        first start;
        then merge approachLoop;
        
        then action measureDistance {
            out attribute distance : PicometerLength;
        }
        then assign currentDistance := measureDistance.distance;
        
        then action checkTunneling {
            in attribute distance = currentDistance;
            out attribute tunneling : Boolean;
        }
        then assign tunnelingDetected := checkTunneling.tunneling;
        
        then decide;
            if tunnelingDetected then establishContact;
            else continueApproach;
        
        action continueApproach {
            in attribute speed = approachSpeed;
        }
        then approachLoop;
        
        action establishContact {
            out attribute contactEstablished = true;
        }
        then done;
    }
    
    action def ManipulateAtom {
        doc /* Move atom to target position */
        in attribute atom : AtomicTarget;
        in attribute targetPosition : SpatialCoordinate;
        out attribute manipulationSuccess : Boolean;
        
        first start;
        then action approach : ApproachAtom {
            in attribute targetAtom = atom;
            in attribute approachSpeed = 0.1;
            out attribute contactEstablished;
        }
        then decide;
            if approach.contactEstablished then attachAtom;
            else failManipulation;
        
        action attachAtom {
            in attribute target = atom;
        }
        then action moveToPosition {
            in attribute destination = targetPosition;
            out attribute positionReached : Boolean;
        }
        then action releaseAtom {
            out attribute releaseSuccess : Boolean;
        }
        then action verifyPlacement {
            in attribute expected = targetPosition;
            out attribute verified : Boolean;
        }
        then decide;
            if verifyPlacement.verified then successManipulation;
            else failManipulation;
        
        action successManipulation {
            out attribute manipulationSuccess = true;
        }
        then done;
        
        action failManipulation {
            out attribute manipulationSuccess = false;
        }
        then done;
    }
    
    action def AssembleMolecularStructure {
        doc /* Assemble complex molecular structure atom by atom */
        in attribute assemblyPlan : ManipulationSequence;
        out attribute completedStructure : AssembledStructure;
        
        private attribute currentAtomIndex : Integer := 1;
        private attribute assembledAtoms : AtomicTarget[*] := ();
        private attribute allSuccessful : Boolean := true;
        
        first start;
        then action scanWorkspace : ScanTargetArea {
            in attribute scanRegion = 100.0;
            in attribute resolution = 1.0;
            out attribute detectedAtoms;
        }
        
        then merge assemblyLoop;
        
        then decide;
            if currentAtomIndex <= 10 then processAtom;
            else finalizeStructure;
        
        action processAtom {
            first start;
            then action selectAtom {
                out attribute selectedAtom : AtomicTarget;
            }
            then action manipulate : ManipulateAtom {
                in attribute atom = selectAtom.selectedAtom;
                in attribute targetPosition;
                out attribute manipulationSuccess;
            }
            then decide;
                if manipulate.manipulationSuccess then recordSuccess;
                else recordFailure;
            
            action recordSuccess {
                then assign assembledAtoms := assembledAtoms->including(selectAtom.selectedAtom);
            }
            then incrementIndex;
            
            action recordFailure {
                then assign allSuccessful := false;
            }
            then incrementIndex;
            
            action incrementIndex {
                then assign currentAtomIndex := currentAtomIndex + 1;
            }
            then done;
        }
        then assemblyLoop;
        
        action finalizeStructure {
            first start;
            then action createStructure {
                out attribute structure : AssembledStructure;
            }
            then assign completedStructure := createStructure.structure;
            then done;
        }
        then done;
    }
    
    state def SystemOperationalStates {
        doc /* Operating states of picotechnology system */
        
        entry; then initializing;
        
        state initializing {
            doc /* System initialization and calibration */
            entry action init : InitializeSystem;
        }
        
        transition initializing to ready
            accept command.initComplete;
        
        state ready {
            doc /* System ready for operations */
        }
        
        transition ready to scanning
            accept command.startScan;
        
        state scanning {
            doc /* Scanning target area */
            entry action scan : ScanTargetArea;
        }
        
        transition scanning to manipulating
            accept command.beginManipulation;
        
        state manipulating {
            doc /* Actively manipulating atoms */
            entry action manipulate : ManipulateAtom;
        }
        
        transition manipulating to assembling
            accept command.startAssembly;
        
        state assembling {
            doc /* Assembling molecular structure */
            entry action assemble : AssembleMolecularStructure;
        }
        
        transition assembling to verifying
            accept command.assemblyComplete;
        
        state verifying {
            doc /* Verifying assembled structure */
        }
        
        transition verifying to ready
            accept command.verificationComplete;
        
        transition scanning to ready
            accept command.abort;
        
        transition manipulating to ready
            accept command.abort;
        
        transition assembling to ready
            accept command.abort;
    }
    
    requirement def PrecisionRequirement {
        doc /* System must achieve picometer-scale positioning precision */
        subject system : PicotechnologyNanoManipulationSystem;
        require constraint {
            system.probe.tipRadius <= 100.0
        }
    }
    
    requirement def VacuumRequirement {
        doc /* System must operate in ultra-high vacuum */
        subject system : PicotechnologyNanoManipulationSystem;
        require constraint {
            system.vacuumChamber.baselinePressure <= 1.0e-10
        }
    }
    
    requirement def ImagingResolutionRequirement {
        doc /* System must achieve atomic-resolution imaging */
        subject system : PicotechnologyNanoManipulationSystem;
        require constraint {
            system.imager.imagingResolution <= 50.0
        }
    }
    
    requirement def ManipulationAccuracyRequirement {
        doc /* System must position atoms with sub-nanometer accuracy */
        subject system : PicotechnologyNanoManipulationSystem;
        require constraint {
            system.feedbackSystem.measurementAccuracy <= 10.0
        }
    }
    
    requirement def ThermalStabilityRequirement {
        doc /* System must maintain stable cryogenic temperature */
        subject system : PicotechnologyNanoManipulationSystem;
        require constraint {
            system.vacuumChamber.operatingTemperature <= 10.0
        }
    }
    
    requirement <'PICO-SYS-001'> systemRequirements {
        doc /* Top-level requirements for picotechnology manipulation system */
        
        require PrecisionRequirement;
        require VacuumRequirement;
        require ImagingResolutionRequirement;
        require ManipulationAccuracyRequirement;
        require ThermalStabilityRequirement;
    }
    
    part def PicotechnologyNanoManipulationSystem {
        doc /* 
            Atomic-scale manipulation system for precise positioning and assembly 
            of individual atoms and molecules.
            
            Primary Function: The system manipulates individual atoms with picometer-level 
            precision to construct custom molecular structures atom-by-atom. It operates by 
            scanning a surface to identify target atoms, approaching them with an ultra-sharp 
            probe tip, attaching individual atoms through controlled forces, and precisely 
            positioning them according to a programmed assembly sequence.
        */
        
        part probe : ScanningProbe {
            attribute tipRadius = 50.0;
            attribute resonanceFrequency = 100.0;
        }
        
        part forceController : AtomicForceController {
            attribute forceSetpoint = 100.0;
            attribute controlBandwidth = 10.0;
        }
        
        part imager : HighResolutionImager {
            attribute imagingResolution = 30.0;
            attribute scanSpeed = 1.0;
        }
        
        part vacuumChamber : UltraHighVacuumChamber {
            attribute baselinePressure = 1.0e-11;
            attribute operatingTemperature = 4.2;
        }
        
        part feedbackSystem : PositionFeedbackSystem {
            attribute measurementAccuracy = 5.0;
            attribute updateRate = 100.0;
        }
        
        part atomReservoir : AtomicReservoir {
            attribute availableTypes = (MoleculeType::carbon, MoleculeType::silicon, 
                                       MoleculeType::hydrogen, MoleculeType::oxygen);
            attribute atomSupplyRate = 10.0;
        }
        
        connection probeControl connect forceController.commandOut to probe.probeControl;
        connection feedbackLoop connect feedbackSystem.sensorInput to forceController.feedbackIn;
        connection imagingControl connect imager.imagingControl to probe.probeControl;
        connection environmentControl connect vacuumChamber.vacuumControl to probe.probeControl;
        
        perform action initialize : InitializeSystem;
        perform action primaryOperation : AssembleMolecularStructure;
        
        exhibit state operatingStates : SystemOperationalStates;
    }
    
    part picotechnologySystem : PicotechnologyNanoManipulationSystem {
        satisfy systemRequirements;
    }
}

// --- Test harness (auto-generated) ---
package ExecutionHarness {
    private import ScalarValues::*;
    private import ISQ::*;
    private import SI::*;
    private import PicotechnologyNanoManipulationSystem::*;

    part testSubject : PicotechnologyNanoManipulationSystem {
        exhibit state operatingStates : SystemOperationalStates;
    }
}

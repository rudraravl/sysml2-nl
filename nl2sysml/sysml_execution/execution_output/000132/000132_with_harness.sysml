package 'For Loop Example' {
	private import SequenceFunctions::*;
	
    action def StraightLineDynamics {
        in power : ISQ::PowerValue;
        in mass : ISQ::MassValue;
        in delta_t : ISQ::TimeValue;
        in x_in : ISQ::LengthValue;
        in v_in : ISQ::SpeedValue;
        out x_out : ISQ::LengthValue;
        out v_out : ISQ::SpeedValue;
    }
	    
	action def ComputeMotion {
		in attribute powerProfile :> ISQ::power[*];
		in attribute vehicleMass :> ISQ::mass;
		in attribute initialPosition :> ISQ::length;
		in attribute initialSpeed :> ISQ::speed;
		in attribute deltaT :> ISQ::time;
		out attribute positions :> ISQ::length[*] := ( );
		
		private attribute position := initialPosition;
		private attribute speed := initialSpeed;
		
		for vehiclePower in powerProfile {
			perform action dynamics : StraightLineDynamics {
				in power = vehiclePower;
				in mass = vehicleMass;
				in delta_t = deltaT;
				in x_in = position;
				in v_in = speed;
				out x_out;
				out v_out;
			}
			then assign position := dynamics.x_out;
			then assign speed := dynamics.v_out;
			then assign positions := positions->including(position);
		}
	}
	
}

// --- Test harness (auto-generated) ---
package ExecutionHarness {
    private import SequenceFunctions::*;
    private import 'For Loop Example'::*;

    action orchestrator {
        attribute testPower : ISQ::PowerValue;
        attribute testMass : ISQ::MassValue;
        attribute testDelta_t : ISQ::TimeValue;
        attribute testX_in : ISQ::LengthValue;
        attribute testV_in : ISQ::SpeedValue;
        action actionProbe : StraightLineDynamics {
            in power = testPower;
            in mass = testMass;
            in delta_t = testDelta_t;
            in x_in = testX_in;
            in v_in = testV_in;
        }
        first actionProbe;
    }
}

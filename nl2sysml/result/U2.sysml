// Create a model for a drone with a battery, a motor, and an altitude sensor.
package DroneModel {
    part def Drone {
        part battery;
        part motor;
        part altitudeSensor;
    }
}
